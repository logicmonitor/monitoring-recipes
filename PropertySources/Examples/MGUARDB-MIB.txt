--
-- MIB Definitions for mGuard 8.7.0
--
-- Copyright 2003-2018 PHOENIX CONTACT Cyber Security AG
-- All Rights Reserved.
--
MGUARDB-MIB DEFINITIONS ::= BEGIN

IMPORTS
  OBJECT-TYPE
    FROM RFC-1212
  TEXTUAL-CONVENTION, RowStatus, MacAddress
    FROM SNMPv2-TC
  enterprises, IpAddress
    FROM RFC1155-SMI
  DisplayString
    FROM RFC1213-MIB
  TRAP-TYPE
    FROM RFC-1215;

MGuardActionStatus ::= TEXTUAL-CONVENTION
  STATUS mandatory
  DESCRIPTION
    "The action status is used to prepare or submit an action, and to
    obtain its status, i.e. whether it is being prepared, running, or
    has been completed. The following steps are performed to run an
    action and obtain the result:

    - Set the action status to 'prepare'. This clears the result from
      running the action previously (if any) and resets its parameters
      to default values.

    - Set the parameters (if any). The parameters can only be set while
      the status is 'prepare'.

    - Set the action status to 'submit'. The action is run.

    - Read the action status. If it is 'running', the action is running.
      Any partial result already produced can be read from the result
      object. If it is 'success', the action has finished running, and
      the outcome can be read from the result object. If it is
      'rejected', running the action was rejected due to an invalid
      parameter, and an error message can be read from the result object.

    - Read the result, then set the action status to 'prepare' to clear
      it.

    The action status can be set to 'prepare' or 'submit'; reading it
    can return 'prepare', 'running', 'success', or 'failed'. It is not
    possible to set the action status while an action is running.

    Once an action has been run, it cannot be re-run without setting the
    action status to 'prepare' first.

    The action status value 'failed' is currently unused and reserved
    for future extensions (i.e. distinguishing between a successful and an
    unsuccessful outcome of running an action)."
  SYNTAX INTEGER {
    prepare(1),
    submit(2),
    running(3),
    success(4),
    rejected(5),
    failed(6)
  }

innominate                         OBJECT IDENTIFIER ::= { enterprises 15450 }
mGuardb                            OBJECT IDENTIFIER ::= { innominate 2 }
mGuardVPN                          OBJECT IDENTIFIER ::= { mGuardb 1 }
mGuardFirewall                     OBJECT IDENTIFIER ::= { mGuardb 2 }
mGuardNetwork                      OBJECT IDENTIFIER ::= { mGuardb 3 }
mGuardSystem                       OBJECT IDENTIFIER ::= { mGuardb 4 }
mGuardSNMP                         OBJECT IDENTIFIER ::= { mGuardb 5 }
mGuardNTP                          OBJECT IDENTIFIER ::= { mGuardb 6 }
mGuardUpdate                       OBJECT IDENTIFIER ::= { mGuardb 7 }
mGuardRedundancy                   OBJECT IDENTIFIER ::= { mGuardb 9 }
mGuardInfo                         OBJECT IDENTIFIER ::= { mGuardb 10 }
mGuardLogging                      OBJECT IDENTIFIER ::= { mGuardb 11 }
mGuardContFilt                     OBJECT IDENTIFIER ::= { mGuardb 12 }
mGuardBlade                        OBJECT IDENTIFIER ::= { mGuardb 13 }
mGuardProfile                      OBJECT IDENTIFIER ::= { mGuardb 14 }
mGuardUsers                        OBJECT IDENTIFIER ::= { mGuardb 15 }
mGuardCerts                        OBJECT IDENTIFIER ::= { mGuardb 16 }
mGuardQoS                          OBJECT IDENTIFIER ::= { mGuardb 17 }
mGuardSECStick                     OBJECT IDENTIFIER ::= { mGuardb 18 }
mGuardCIFS                         OBJECT IDENTIFIER ::= { mGuardb 20 }
mGuardSecCloud                     OBJECT IDENTIFIER ::= { mGuardb 21 }
mGuardOpenVPN                      OBJECT IDENTIFIER ::= { mGuardb 22 }
mGuardVPNMachine                   OBJECT IDENTIFIER ::= { mGuardVPN 1 }
mGuardVPNTunnel                    OBJECT IDENTIFIER ::= { mGuardVPN 7 }
mGuardVPNFW                        OBJECT IDENTIFIER ::= { mGuardVPN 3 }
mGuardVPNIkePref                   OBJECT IDENTIFIER ::= { mGuardVPN 9 }
mGuardVPNIPsecPref                 OBJECT IDENTIFIER ::= { mGuardVPN 10 }
mGuardVPNDynDNS                    OBJECT IDENTIFIER ::= { mGuardVPN 4 }
mGuardVPNDynDNSRegister            OBJECT IDENTIFIER ::= { mGuardVPNDynDNS 1 }
mGuardVPNDynDNSCheck               OBJECT IDENTIFIER ::= { mGuardVPNDynDNS 2 }
mGuardVPNL2TP                      OBJECT IDENTIFIER ::= { mGuardVPN 5 }
mGuardVPNSettings                  OBJECT IDENTIFIER ::= { mGuardVPN 6 }
mGuardVPNLogPersist                OBJECT IDENTIFIER ::= { mGuardVPNSettings 20 }
mGuardVPNModeCfgXauth              OBJECT IDENTIFIER ::= { mGuardVPN 11 }
mGuardVPNModeCfgServerLocNets      OBJECT IDENTIFIER ::= { mGuardVPNModeCfgXauth 1 }
mGuardVPNModeCfgServerRemNets      OBJECT IDENTIFIER ::= { mGuardVPNModeCfgXauth 2 }
mGuardFirewallIncoming             OBJECT IDENTIFIER ::= { mGuardFirewall 1 }
mGuardFirewallOutgoing             OBJECT IDENTIFIER ::= { mGuardFirewall 2 }
mGuardFirewallPortforwarding       OBJECT IDENTIFIER ::= { mGuardFirewall 3 }
mGuardFirewallNAT                  OBJECT IDENTIFIER ::= { mGuardFirewall 4 }
mGuardFirewallExtended             OBJECT IDENTIFIER ::= { mGuardFirewall 5 }
mGuardFirewall11NAT                OBJECT IDENTIFIER ::= { mGuardFirewall 6 }
mGuardFWUsrFW                      OBJECT IDENTIFIER ::= { mGuardFirewall 7 }
mGuardFirewallRules                OBJECT IDENTIFIER ::= { mGuardFirewall 8 }
mGuardFirewallIncomingWanDmz       OBJECT IDENTIFIER ::= { mGuardFirewall 10 }
mGuardFirewallIncomingDmzLan       OBJECT IDENTIFIER ::= { mGuardFirewall 11 }
mGuardFirewallOutgoingDmzWan       OBJECT IDENTIFIER ::= { mGuardFirewall 12 }
mGuardFirewallOutgoingLanDmz       OBJECT IDENTIFIER ::= { mGuardFirewall 13 }
mGuardFirewallGroupIPv4            OBJECT IDENTIFIER ::= { mGuardFirewall 14 }
mGuardFirewallGroupPort            OBJECT IDENTIFIER ::= { mGuardFirewall 15 }
mGuardFirewallModbus               OBJECT IDENTIFIER ::= { mGuardFirewall 16 }
mGuardStealth                      OBJECT IDENTIFIER ::= { mGuardNetwork 2 }
mGuardStealthIPConfStatic          OBJECT IDENTIFIER ::= { mGuardStealth 2 }
mGuardStealthL2Filter              OBJECT IDENTIFIER ::= { mGuardStealth 5 }
mGuardStealthInterface             OBJECT IDENTIFIER ::= { mGuardStealth 6 }
mGuardStealthIPConfAutoDetect      OBJECT IDENTIFIER ::= { mGuardStealth 7 }
mGuardRouter                       OBJECT IDENTIFIER ::= { mGuardNetwork 3 }
mGuardRouterLocal                  OBJECT IDENTIFIER ::= { mGuardRouter 1 }
mGuardRouterExtern                 OBJECT IDENTIFIER ::= { mGuardRouter 2 }
mGuardRouterExternStatic           OBJECT IDENTIFIER ::= { mGuardRouterExtern 2 }
mGuardRouterHiDiscovery            OBJECT IDENTIFIER ::= { mGuardRouter 3 }
mGuardRouterDmz                    OBJECT IDENTIFIER ::= { mGuardRouter 4 }
mGuardPPPOE                        OBJECT IDENTIFIER ::= { mGuardNetwork 4 }
mGuardDHCP                         OBJECT IDENTIFIER ::= { mGuardNetwork 5 }
mGuardDHCPInt                      OBJECT IDENTIFIER ::= { mGuardDHCP 1 }
mGuardDHCPExt                      OBJECT IDENTIFIER ::= { mGuardDHCP 2 }
mGuardDHCPDmz                      OBJECT IDENTIFIER ::= { mGuardDHCP 3 }
mGuardDNS                          OBJECT IDENTIFIER ::= { mGuardNetwork 6 }
mGuardDNSZones                     OBJECT IDENTIFIER ::= { mGuardDNS 7 }
mGuardNetworkStatus                OBJECT IDENTIFIER ::= { mGuardNetwork 7 }
mGuardPPTP                         OBJECT IDENTIFIER ::= { mGuardNetwork 10 }
mGuardSerial                       OBJECT IDENTIFIER ::= { mGuardNetwork 11 }
mGuardSerialPPP                    OBJECT IDENTIFIER ::= { mGuardSerial 3 }
mGuardSerialPPPFWIN                OBJECT IDENTIFIER ::= { mGuardSerialPPP 6 }
mGuardSerialPPPFWOUT               OBJECT IDENTIFIER ::= { mGuardSerialPPP 7 }
mGuardSerialComServer              OBJECT IDENTIFIER ::= { mGuardSerial 4 }
mGuardModem                        OBJECT IDENTIFIER ::= { mGuardNetwork 13 }
mGuardModemPAP                     OBJECT IDENTIFIER ::= { mGuardModem 12 }
mGuardModemCHAP                    OBJECT IDENTIFIER ::= { mGuardModem 13 }
mGuardProxy                        OBJECT IDENTIFIER ::= { mGuardNetwork 14 }
mGuardProxyHTTP                    OBJECT IDENTIFIER ::= { mGuardProxy 80 }
mGuardNetworkExt2                  OBJECT IDENTIFIER ::= { mGuardNetwork 15 }
mGuardNetworkExt2Probe             OBJECT IDENTIFIER ::= { mGuardNetworkExt2 3 }
mGuardGsm                          OBJECT IDENTIFIER ::= { mGuardNetwork 23 }
mGuardGsmSim1                      OBJECT IDENTIFIER ::= { mGuardGsm 1 }
mGuardGsmSim2                      OBJECT IDENTIFIER ::= { mGuardGsm 2 }
mGuardIgmp                         OBJECT IDENTIFIER ::= { mGuardNetwork 24 }
mGuardMirror                       OBJECT IDENTIFIER ::= { mGuardNetwork 25 }
mGuardStaticMulticast              OBJECT IDENTIFIER ::= { mGuardNetwork 26 }
mGuardDynRouting                   OBJECT IDENTIFIER ::= { mGuardNetwork 27 }
mGuardOSPF                         OBJECT IDENTIFIER ::= { mGuardDynRouting 1 }
mGuardGRETunnel                    OBJECT IDENTIFIER ::= { mGuardNetwork 28 }
mGuardPasswords                    OBJECT IDENTIFIER ::= { mGuardSystem 1 }
mGuardHTTPSRemoteAccess            OBJECT IDENTIFIER ::= { mGuardSystem 2 }
mGuardHTTPSX509                    OBJECT IDENTIFIER ::= { mGuardHTTPSRemoteAccess 5 }
mGuardSSHRemoteAccess              OBJECT IDENTIFIER ::= { mGuardSystem 3 }
mGuardSSHX509                      OBJECT IDENTIFIER ::= { mGuardSSHRemoteAccess 5 }
mGuardWebInterface                 OBJECT IDENTIFIER ::= { mGuardSystem 4 }
mGuardHardwareInformation          OBJECT IDENTIFIER ::= { mGuardSystem 5 }
mGuardVersions                     OBJECT IDENTIFIER ::= { mGuardSystem 7 }
mGuardKeyboardSettings             OBJECT IDENTIFIER ::= { mGuardSystem 10 }
mGuardEmailSetting                 OBJECT IDENTIFIER ::= { mGuardSystem 11 }
mGuardGPS                          OBJECT IDENTIFIER ::= { mGuardSystem 13 }
mGuardService                      OBJECT IDENTIFIER ::= { mGuardSystem 14 }
mGuardEnrolled                     OBJECT IDENTIFIER ::= { mGuardSystem 16 }
mGuardSNMPTrapConfigGroup          OBJECT IDENTIFIER ::= { mGuardSNMP 8 }
mGuardLLDP                         OBJECT IDENTIFIER ::= { mGuardSNMP 11 }
mGuardL2Redundancy                 OBJECT IDENTIFIER ::= { mGuardRedundancy 1 }
mGuardRouterRedundancy             OBJECT IDENTIFIER ::= { mGuardRedundancy 2 }
mGuardRedundancyState              OBJECT IDENTIFIER ::= { mGuardRedundancy 3 }
mGuardL2RedState                   OBJECT IDENTIFIER ::= { mGuardRedundancyState 1 }
mGuardRRedState                    OBJECT IDENTIFIER ::= { mGuardRedundancyState 2 }
mGuardRRedStateAC                  OBJECT IDENTIFIER ::= { mGuardRRedState 3 }
mGuardRRedStateCC                  OBJECT IDENTIFIER ::= { mGuardRRedState 4 }
mGuardRRedStateStateRep            OBJECT IDENTIFIER ::= { mGuardRRedState 5 }
mGuardRRedStatePhraseSwap          OBJECT IDENTIFIER ::= { mGuardRRedState 6 }
mGuardTrapResources                OBJECT IDENTIFIER ::= { mGuardInfo 4 }
mGuardTResAV                       OBJECT IDENTIFIER ::= { mGuardTrapResources 6 }
mGuardTResPlatformSpecific         OBJECT IDENTIFIER ::= { mGuardTrapResources 7 }
mGuardTResIndustrial               OBJECT IDENTIFIER ::= { mGuardTResPlatformSpecific 1 }
mGuardTResIndustrialPower          OBJECT IDENTIFIER ::= { mGuardTResIndustrial 1 }
mGuardTResIndustrialTemperature    OBJECT IDENTIFIER ::= { mGuardTResIndustrial 2 }
mGuardTResSignalRelais             OBJECT IDENTIFIER ::= { mGuardTResIndustrial 3 }
mGuardTResSignalLinkTable          OBJECT IDENTIFIER ::= { mGuardTResIndustrial 5 }
mGuardTResCMD                      OBJECT IDENTIFIER ::= { mGuardTResIndustrial 6 }
mGuardTResBladeCTRL                OBJECT IDENTIFIER ::= { mGuardTResPlatformSpecific 2 }
mGuardTResBladeInfo                OBJECT IDENTIFIER ::= { mGuardTResBladeCTRL 1 }
mGuardTResBladeCtrlCfg             OBJECT IDENTIFIER ::= { mGuardTResBladeCTRL 5 }
mGuardTResRedundancy               OBJECT IDENTIFIER ::= { mGuardTrapResources 8 }
mGuardTResUserFirewall             OBJECT IDENTIFIER ::= { mGuardTrapResources 10 }
mGuardTResVPN                      OBJECT IDENTIFIER ::= { mGuardTrapResources 11 }
mGuardTResSSH                      OBJECT IDENTIFIER ::= { mGuardTrapResources 12 }
mGuardTResSECStick                 OBJECT IDENTIFIER ::= { mGuardTrapResources 13 }
mGuardTResCIFSScan                 OBJECT IDENTIFIER ::= { mGuardTrapResources 16 }
mGuardContFiltAVP                  OBJECT IDENTIFIER ::= { mGuardContFilt 1 }
mGuardContFiltHTTP                 OBJECT IDENTIFIER ::= { mGuardContFilt 2 }
mGuardContFiltPOP3                 OBJECT IDENTIFIER ::= { mGuardContFilt 3 }
mGuardContFiltSMTP                 OBJECT IDENTIFIER ::= { mGuardContFilt 4 }
mGuardContFiltFTP                  OBJECT IDENTIFIER ::= { mGuardContFilt 5 }
mGuardContFiltAVPHTTPProxy         OBJECT IDENTIFIER ::= { mGuardContFiltAVP 3 }
mGuardContFiltAVPpass              OBJECT IDENTIFIER ::= { mGuardContFiltAVP 8 }
mGuardContFiltQuarantine           OBJECT IDENTIFIER ::= { mGuardContFiltAVP 9 }
mGuardContFiltInfo                 OBJECT IDENTIFIER ::= { mGuardContFiltAVP 10 }
mGuardProfilePush                  OBJECT IDENTIFIER ::= { mGuardProfile 1 }
mGuardProfilePull                  OBJECT IDENTIFIER ::= { mGuardProfile 2 }
mGuardProfilePullHTTPS             OBJECT IDENTIFIER ::= { mGuardProfilePull 2 }
mGuardProfileECS                   OBJECT IDENTIFIER ::= { mGuardProfile 3 }
mGuardRemoteUsers                  OBJECT IDENTIFIER ::= { mGuardUsers 1 }
mGuardRADIUS                       OBJECT IDENTIFIER ::= { mGuardRemoteUsers 1 }
mGuardUserFWUsers                  OBJECT IDENTIFIER ::= { mGuardRemoteUsers 2 }
mGuardCertsLocal                   OBJECT IDENTIFIER ::= { mGuardCerts 1 }
mGuardCertsCA                      OBJECT IDENTIFIER ::= { mGuardCerts 2 }
mGuardCertsRemote                  OBJECT IDENTIFIER ::= { mGuardCerts 3 }
mGuardCertsCRL                     OBJECT IDENTIFIER ::= { mGuardCerts 4 }
mGuardQoSIng                       OBJECT IDENTIFIER ::= { mGuardQoS 1 }
mGuardQoSIngIntern                 OBJECT IDENTIFIER ::= { mGuardQoSIng 1 }
mGuardQoSIngExtern                 OBJECT IDENTIFIER ::= { mGuardQoSIng 2 }
mGuardQoSEg                        OBJECT IDENTIFIER ::= { mGuardQoS 2 }
mGuardQoSEgIntern                  OBJECT IDENTIFIER ::= { mGuardQoSEg 1 }
mGuardQoSEgExtern                  OBJECT IDENTIFIER ::= { mGuardQoSEg 2 }
mGuardQoSEgVPNExtern               OBJECT IDENTIFIER ::= { mGuardQoSEg 3 }
mGuardQoSEgVPNIntern               OBJECT IDENTIFIER ::= { mGuardQoSEg 4 }
mGuardQoSEgExtern2                 OBJECT IDENTIFIER ::= { mGuardQoSEg 5 }
mGuardQoSEgVPNExtern2              OBJECT IDENTIFIER ::= { mGuardQoSEg 6 }
mGuardQoSEgDialin                  OBJECT IDENTIFIER ::= { mGuardQoSEg 7 }
mGuardQoSEgVPNDialin               OBJECT IDENTIFIER ::= { mGuardQoSEg 8 }
mGuardQoSSupport                   OBJECT IDENTIFIER ::= { mGuardQoS 3 }
mGuardSECStickTunnel               OBJECT IDENTIFIER ::= { mGuardSECStick 7 }
mGuardSECStickRemote               OBJECT IDENTIFIER ::= { mGuardSECStick 8 }
mGuardCIFSShare                    OBJECT IDENTIFIER ::= { mGuardCIFS 1 }
mGuardCIFSInt                      OBJECT IDENTIFIER ::= { mGuardCIFS 2 }
mGuardCIFSAVScanConnector          OBJECT IDENTIFIER ::= { mGuardCIFS 4 }
mGuardTrapAV                       OBJECT IDENTIFIER ::= { mGuardInfo 6 }
mGuardTrapPlatformSpecific         OBJECT IDENTIFIER ::= { mGuardInfo 7 }
mGuardTrapIndustrial               OBJECT IDENTIFIER ::= { mGuardTrapPlatformSpecific 1 }
mGuardTrapBladeCTRL                OBJECT IDENTIFIER ::= { mGuardTrapPlatformSpecific 2 }
mGuardTrapBladeCtrlCfg             OBJECT IDENTIFIER ::= { mGuardTrapBladeCTRL 5 }
mGuardTrapRouterRedundancy         OBJECT IDENTIFIER ::= { mGuardInfo 8 }
mGuardTrapUserFirewall             OBJECT IDENTIFIER ::= { mGuardInfo 9 }
mGuardTrapVPN                      OBJECT IDENTIFIER ::= { mGuardInfo 11 }
mGuardTrapSSH                      OBJECT IDENTIFIER ::= { mGuardInfo 12 }
mGuardTrapSECStick                 OBJECT IDENTIFIER ::= { mGuardInfo 13 }
mGuardTrapCIFSScan                 OBJECT IDENTIFIER ::= { mGuardInfo 16 }
mGuardTrapGSM                      OBJECT IDENTIFIER ::= { mGuardInfo 17 }
mGuardTrapCMD                      OBJECT IDENTIFIER ::= { mGuardInfo 18 }
mGuardSecCloudEngine               OBJECT IDENTIFIER ::= { mGuardSecCloud 1 }
mGuardSecCloudDirFac               OBJECT IDENTIFIER ::= { mGuardSecCloud 6 }
mGuardEDS                          OBJECT IDENTIFIER ::= { mGuardSystem 12 }
mGuardActions                      OBJECT IDENTIFIER ::= { mGuardSystem 15 }

-- ARP_LIMIT_EXT
mGuardFirewallARPLimitExt OBJECT-TYPE
  SYNTAX INTEGER
  ACCESS read-write
  STATUS mandatory
  DESCRIPTION
    "Variable name: ARP_LIMIT_EXT
    WebUi Label: Incoming
    Maximum number of incoming ARP request frames per second (stealth mode
    only)"
  ::= { mGuardFirewallExtended 10 }

-- ARP_LIMIT_INT
mGuardFirewallARPLimitInt OBJECT-TYPE
  SYNTAX INTEGER
  ACCESS read-write
  STATUS mandatory
  DESCRIPTION
    "Variable name: ARP_LIMIT_INT
    WebUi Label: Outgoing
    Maximum number of outgoing ARP request frames per second (stealth mode
    only)"
  ::= { mGuardFirewallExtended 9 }

-- ARP_TIMEOUT
mGuardArpTimeout OBJECT-TYPE
  SYNTAX INTEGER
  ACCESS read-write
  STATUS mandatory
  DESCRIPTION
    "Variable name: ARP_TIMEOUT
    WebUi Label: ARP timeout
    Global ARP timeout in seconds."
  ::= { mGuardNetwork 12 }

-- AUDIT_PASSWORD
mGuardAuditPassword OBJECT-TYPE
  SYNTAX DisplayString
  ACCESS read-write
  STATUS mandatory
  DESCRIPTION
    "Variable name: AUDIT_PASSWORD
    WebUi Label: --
    Changes the password for the user 'audit', who can only view the
    systems configuration."
  ::= { mGuardPasswords 6 }


-- CA_CERTS table
mGuardCertsCATable OBJECT-TYPE
  SYNTAX SEQUENCE OF MGuardCertsCAEntry
  ACCESS not-accessible
  STATUS mandatory
  DESCRIPTION
    "A table of CA_CERTS"
  ::= { mGuardCertsCA 1 }

-- CA_CERTS table entry
mGuardCertsCAEntry OBJECT-TYPE
  SYNTAX MGuardCertsCAEntry
  ACCESS not-accessible
  STATUS mandatory
  DESCRIPTION
    "An entry of CA_CERTS"
  INDEX { mGuardCertsCAIndex }
  ::= { mGuardCertsCATable 1 }

MGuardCertsCAEntry ::= SEQUENCE {
  mGuardCertsCAIndex                       INTEGER,
  mGuardCertsCAName                        DisplayString,
  mGuardCertsCACertificate                 DisplayString,
  mGuardCertsCARowStatus                   RowStatus
}

-- CA_CERTS table index
mGuardCertsCAIndex OBJECT-TYPE
  SYNTAX INTEGER (1..2147483647)
  ACCESS not-accessible
  STATUS mandatory
  DESCRIPTION
    "Index to CA_CERTS"
  ::= { mGuardCertsCAEntry 1 }

-- CA_CERTS row status
mGuardCertsCARowStatus OBJECT-TYPE
  SYNTAX RowStatus
  ACCESS read-write
  STATUS mandatory
  DESCRIPTION
    "RowStatus of CA_CERTS"
  ::= { mGuardCertsCAEntry 50 }

-- CA_CERTS.FRIENDLY_NAME
mGuardCertsCAName OBJECT-TYPE
  SYNTAX DisplayString
  ACCESS read-write
  STATUS mandatory
  DESCRIPTION
    "Variable name: CA_CERTS.FRIENDLY_NAME
    WebUi Label: Short name
    A user defined name for the CA certificate, which is also used to
    reference the certificate."
  ::= { mGuardCertsCAEntry 2 }

-- CA_CERTS.CERTIFICATE
mGuardCertsCACertificate OBJECT-TYPE
  SYNTAX DisplayString
  ACCESS read-write
  STATUS mandatory
  DESCRIPTION
    "Variable name: CA_CERTS.CERTIFICATE
    WebUi Label: --
    The certificate."
  ::= { mGuardCertsCAEntry 3 }

-- CERT_ENROLL_CA_DIR
mGuardEnrollCADir OBJECT-TYPE
  SYNTAX DisplayString
  ACCESS read-write
  STATUS mandatory
  DESCRIPTION
    "Variable name: CERT_ENROLL_CA_DIR
    WebUi Label: Directory
    Directory on the CA server for renewing the enrolled certificate"
  ::= { mGuardEnrolled 6 }

-- CERT_ENROLL_CA_HOST
mGuardEnrollCAHost OBJECT-TYPE
  SYNTAX DisplayString
  ACCESS read-write
  STATUS mandatory
  DESCRIPTION
    "Variable name: CERT_ENROLL_CA_HOST
    WebUi Label: Server
    Hostname of the CA responsible for renewing the enrolled certificate"
  ::= { mGuardEnrolled 3 }

-- CERT_ENROLL_CA_PORT
mGuardEnrollCAPort OBJECT-TYPE
  SYNTAX INTEGER(1..65535)
  ACCESS read-write
  STATUS mandatory
  DESCRIPTION
    "Variable name: CERT_ENROLL_CA_PORT
    WebUi Label: Port
    Port of the CA server for renewing the enrolled certificate. Usually
    443."
  ::= { mGuardEnrolled 5 }

-- CERT_ENROLL_CA_REF
mGuardEnrollCAValue OBJECT-TYPE
  SYNTAX INTEGER {
    none(1)
  }
  ACCESS read-write
  STATUS mandatory
  DESCRIPTION
    "Variable name: CERT_ENROLL_CA_REF
    WebUi Label: Enrollment root CA certificate
    This object is effective if and only if the 'mGuardEnrollCARef' object
    contains the OID of this object. When this object is read, it always
    returns the value 'none'. When the value 'none' is written to this
    object, no local machine certificate is used."
  ::= { mGuardEnrolled 1 }

-- CERT_ENROLL_CA_REF reference
mGuardEnrollCARef OBJECT-TYPE
  SYNTAX OBJECT IDENTIFIER
  ACCESS read-write
  STATUS mandatory
  DESCRIPTION
    "Variable name: CERT_ENROLL_CA_REF
    WebUi Label: Enrollment root CA certificate
    When this object contains the OID of an 'mGuardCertsCAIndex' object,
    the corresponding X.509 certificate and private key is used to
    identify this site. To select a local machine certificate in this
    manner, write the OID of the corresponding 'mGuardCertsCAIndex' object
    to this object. To disable this feature, set the 'mGuardEnrollCAValue'
    object."
  ::= { mGuardEnrolled 2 }

-- CERT_ENROLL_KEY_UPDATE
mGuardEnrollNewKey OBJECT-TYPE
  SYNTAX INTEGER {
    yes(1),
    no(2)
  }
  ACCESS read-write
  STATUS mandatory
  DESCRIPTION
    "Variable name: CERT_ENROLL_KEY_UPDATE
    WebUi Label: Generate a new key on certificate renewal
    On each renewal a new 4096 bit key will be generated if this option is
    set."
  ::= { mGuardEnrolled 4 }


-- CHECK_PATTERN_SET table
mGuardCIFSIntFilePatSetTable OBJECT-TYPE
  SYNTAX SEQUENCE OF MGuardCIFSIntFilePatSetEntry
  ACCESS not-accessible
  STATUS mandatory
  DESCRIPTION
    "A table of CHECK_PATTERN_SET"
  ::= { mGuardCIFSInt 9 }

-- CHECK_PATTERN_SET table entry
mGuardCIFSIntFilePatSetEntry OBJECT-TYPE
  SYNTAX MGuardCIFSIntFilePatSetEntry
  ACCESS not-accessible
  STATUS mandatory
  DESCRIPTION
    "An entry of CHECK_PATTERN_SET"
  INDEX { mGuardCIFSIntFilePatSetIndex }
  ::= { mGuardCIFSIntFilePatSetTable 1 }

MGuardCIFSIntFilePatSetEntry ::= SEQUENCE {
  mGuardCIFSIntFilePatSetIndex             INTEGER,
  mGuardCIFSIntFilePatSetName              DisplayString,
  mGuardCIFSIntFilePatSetRowStatus         RowStatus
}

-- CHECK_PATTERN_SET table index
mGuardCIFSIntFilePatSetIndex OBJECT-TYPE
  SYNTAX INTEGER (1..2147483647)
  ACCESS not-accessible
  STATUS mandatory
  DESCRIPTION
    "Index to CHECK_PATTERN_SET"
  ::= { mGuardCIFSIntFilePatSetEntry 1 }

-- CHECK_PATTERN_SET row status
mGuardCIFSIntFilePatSetRowStatus OBJECT-TYPE
  SYNTAX RowStatus
  ACCESS read-write
  STATUS mandatory
  DESCRIPTION
    "RowStatus of CHECK_PATTERN_SET"
  ::= { mGuardCIFSIntFilePatSetEntry 3 }


-- CHECK_PATTERN_SET.SET table
mGuardCIFSIntFilePatTable OBJECT-TYPE
  SYNTAX SEQUENCE OF MGuardCIFSIntFilePatEntry
  ACCESS not-accessible
  STATUS mandatory
  DESCRIPTION
    "A table of CHECK_PATTERN_SET.SET"
  ::= { mGuardCIFSInt 10 }

-- CHECK_PATTERN_SET.SET table entry
mGuardCIFSIntFilePatEntry OBJECT-TYPE
  SYNTAX MGuardCIFSIntFilePatEntry
  ACCESS not-accessible
  STATUS mandatory
  DESCRIPTION
    "An entry of CHECK_PATTERN_SET.SET"
  INDEX { mGuardCIFSIntFilePatSetIndex, mGuardCIFSIntFilePatIndex }
  ::= { mGuardCIFSIntFilePatTable 1 }

MGuardCIFSIntFilePatEntry ::= SEQUENCE {
  mGuardCIFSIntFilePatIndex                INTEGER,
  mGuardCIFSIntFilePatCheck                INTEGER,
  mGuardCIFSIntFilePatFilePat              DisplayString,
  mGuardCIFSIntFilePatRowStatus            RowStatus
}

-- CHECK_PATTERN_SET.SET table index
mGuardCIFSIntFilePatIndex OBJECT-TYPE
  SYNTAX INTEGER (1..2147483647)
  ACCESS not-accessible
  STATUS mandatory
  DESCRIPTION
    "Index to CHECK_PATTERN_SET.SET"
  ::= { mGuardCIFSIntFilePatEntry 1 }

-- CHECK_PATTERN_SET.SET row status
mGuardCIFSIntFilePatRowStatus OBJECT-TYPE
  SYNTAX RowStatus
  ACCESS read-write
  STATUS mandatory
  DESCRIPTION
    "RowStatus of CHECK_PATTERN_SET.SET"
  ::= { mGuardCIFSIntFilePatEntry 4 }

-- CHECK_PATTERN_SET.SET.PATTERN
mGuardCIFSIntFilePatFilePat OBJECT-TYPE
  SYNTAX DisplayString
  ACCESS read-write
  STATUS mandatory
  DESCRIPTION
    "Variable name: CHECK_PATTERN_SET.SET.PATTERN
    WebUi Label: Filename pattern
    File pattern (e.g.: '**\*.exe')."
  ::= { mGuardCIFSIntFilePatEntry 3 }

-- CHECK_PATTERN_SET.SET.CHECK
mGuardCIFSIntFilePatCheck OBJECT-TYPE
  SYNTAX INTEGER {
    yes(1),
    no(2)
  }
  ACCESS read-write
  STATUS mandatory
  DESCRIPTION
    "Variable name: CHECK_PATTERN_SET.SET.CHECK
    WebUi Label: Include in check
    Check file pattern: yes/no."
  ::= { mGuardCIFSIntFilePatEntry 2 }

-- CHECK_PATTERN_SET.NAME
mGuardCIFSIntFilePatSetName OBJECT-TYPE
  SYNTAX DisplayString
  ACCESS read-write
  STATUS mandatory
  DESCRIPTION
    "Variable name: CHECK_PATTERN_SET.NAME
    WebUi Label: Name
    Name of the file pattern set"
  ::= { mGuardCIFSIntFilePatSetEntry 2 }


-- CIFS_FILE_CHECK table
mGuardCIFSIntShareTable OBJECT-TYPE
  SYNTAX SEQUENCE OF MGuardCIFSIntShareEntry
  ACCESS not-accessible
  STATUS mandatory
  DESCRIPTION
    "A table of CIFS_FILE_CHECK"
  ::= { mGuardCIFSInt 8 }

-- CIFS_FILE_CHECK table entry
mGuardCIFSIntShareEntry OBJECT-TYPE
  SYNTAX MGuardCIFSIntShareEntry
  ACCESS not-accessible
  STATUS mandatory
  DESCRIPTION
    "An entry of CIFS_FILE_CHECK"
  INDEX { mGuardCIFSIntShareIndex }
  ::= { mGuardCIFSIntShareTable 1 }

MGuardCIFSIntShareEntry ::= SEQUENCE {
  mGuardCIFSIntShareIndex                  INTEGER,
  mGuardCIFSIntShareEnable                 INTEGER,
  mGuardCIFSIntShareScanShareRef           OBJECT IDENTIFIER,
  mGuardCIFSIntShareChksumShareRef         OBJECT IDENTIFIER,
  mGuardCIFSIntShareFilePatRef             OBJECT IDENTIFIER,
  mGuardCIFSIntShareScheduleDay            INTEGER,
  mGuardCIFSIntShareScheduleHour           INTEGER,
  mGuardCIFSIntShareScheduleMinute         INTEGER,
  mGuardCIFSIntShareMaxDuration            INTEGER,
  mGuardCIFSIntShareChksumAlgo             INTEGER,
  mGuardCIFSIntShareChksumFileBase         DisplayString,
  mGuardCIFSIntShareRowStatus              RowStatus,
  mGuardCIFSIntShareScheduleIntervalHours  INTEGER
}

-- CIFS_FILE_CHECK table index
mGuardCIFSIntShareIndex OBJECT-TYPE
  SYNTAX INTEGER (1..2147483647)
  ACCESS not-accessible
  STATUS mandatory
  DESCRIPTION
    "Index to CIFS_FILE_CHECK"
  ::= { mGuardCIFSIntShareEntry 1 }

-- CIFS_FILE_CHECK row status
mGuardCIFSIntShareRowStatus OBJECT-TYPE
  SYNTAX RowStatus
  ACCESS read-write
  STATUS mandatory
  DESCRIPTION
    "RowStatus of CIFS_FILE_CHECK"
  ::= { mGuardCIFSIntShareEntry 12 }

-- CIFS_FILE_CHECK.SCHEDULE_HOUR
mGuardCIFSIntShareScheduleHour OBJECT-TYPE
  SYNTAX INTEGER(0..23)
  ACCESS read-write
  STATUS mandatory
  DESCRIPTION
    "Variable name: CIFS_FILE_CHECK.SCHEDULE_HOUR
    WebUi Label: Start at (hour)
    The hour the scan should start."
  ::= { mGuardCIFSIntShareEntry 7 }

-- CIFS_FILE_CHECK.SCHEDULE
mGuardCIFSIntShareScheduleDay OBJECT-TYPE
  SYNTAX INTEGER {
    monday(1),
    tuesday(2),
    wednesday(3),
    thursday(4),
    friday(5),
    saturday(6),
    sunday(7),
    daily(1000),
    intervalhours(1001),
    continuous(1002)
  }
  ACCESS read-write
  STATUS mandatory
  DESCRIPTION
    "Variable name: CIFS_FILE_CHECK.SCHEDULE
    WebUi Label: Time schedule
    The day of the scan: daily or a specific day of the week."
  ::= { mGuardCIFSIntShareEntry 6 }

-- CIFS_FILE_CHECK.CHECKSUM_FILE_BASE
mGuardCIFSIntShareChksumFileBase OBJECT-TYPE
  SYNTAX DisplayString
  ACCESS read-write
  STATUS mandatory
  DESCRIPTION
    "Variable name: CIFS_FILE_CHECK.CHECKSUM_FILE_BASE
    WebUi Label: Basename of the checksum files (may be prefixed with a directory)
    Basename of checksum-files that the mGuard will store to the checksum-
    share. It is possible to include a subdirectory here, but it must not
    start with a '/'."
  ::= { mGuardCIFSIntShareEntry 11 }

-- CIFS_FILE_CHECK.SCHEDULE_MIN
mGuardCIFSIntShareScheduleMinute OBJECT-TYPE
  SYNTAX INTEGER(0..59)
  ACCESS read-write
  STATUS mandatory
  DESCRIPTION
    "Variable name: CIFS_FILE_CHECK.SCHEDULE_MIN
    WebUi Label: Start at (minute)
    The minute the scan should start."
  ::= { mGuardCIFSIntShareEntry 8 }

-- CIFS_FILE_CHECK.MAX_DURATION_MINUTES
mGuardCIFSIntShareMaxDuration OBJECT-TYPE
  SYNTAX INTEGER(10..1440)
  ACCESS read-write
  STATUS mandatory
  DESCRIPTION
    "Variable name: CIFS_FILE_CHECK.MAX_DURATION_MINUTES
    WebUi Label: Maximum time a check may take
    The max duration of the scan in minutes."
  ::= { mGuardCIFSIntShareEntry 9 }

-- CIFS_FILE_CHECK.ENABLED
mGuardCIFSIntShareEnable OBJECT-TYPE
  SYNTAX INTEGER {
    yes(1),
    no(2),
    suspended(3)
  }
  ACCESS read-write
  STATUS mandatory
  DESCRIPTION
    "Variable name: CIFS_FILE_CHECK.ENABLED
    WebUi Label: Enabled
    Scan share: yes,no,suspended."
  ::= { mGuardCIFSIntShareEntry 2 }

-- CIFS_FILE_CHECK.SCHEDULE_INTERVAL_HOURS
mGuardCIFSIntShareScheduleIntervalHours OBJECT-TYPE
  SYNTAX INTEGER
  ACCESS read-write
  STATUS mandatory
  DESCRIPTION
    "Variable name: CIFS_FILE_CHECK.SCHEDULE_INTERVAL_HOURS
    WebUi Label: Every
    Start a scan every n hours"
  ::= { mGuardCIFSIntShareEntry 13 }

-- CIFS_FILE_CHECK.PATTERNS reference
mGuardCIFSIntShareFilePatRef OBJECT-TYPE
  SYNTAX OBJECT IDENTIFIER
  ACCESS read-write
  STATUS mandatory
  DESCRIPTION
    "Variable name: CIFS_FILE_CHECK.PATTERNS
    WebUi Label: Patterns for filenames
    The OID of an 'mGuardCIFSIntFilePatSetIndex' object that designates
    the file pattern set that is used for the scan."
  ::= { mGuardCIFSIntShareEntry 5 }

-- CIFS_FILE_CHECK.SCANNED_SHARE reference
mGuardCIFSIntShareScanShareRef OBJECT-TYPE
  SYNTAX OBJECT IDENTIFIER
  ACCESS read-write
  STATUS mandatory
  DESCRIPTION
    "Variable name: CIFS_FILE_CHECK.SCANNED_SHARE
    WebUi Label: Checked CIFS share
    The OID of an 'mGuardCIFSShareIndex' object that designates the share
    to be scanned."
  ::= { mGuardCIFSIntShareEntry 3 }

-- CIFS_FILE_CHECK.CHECKSUM_ALGO
mGuardCIFSIntShareChksumAlgo OBJECT-TYPE
  SYNTAX INTEGER {
    md5(1),
    sha(2),
    sha256(3)
  }
  ACCESS read-write
  STATUS mandatory
  DESCRIPTION
    "Variable name: CIFS_FILE_CHECK.CHECKSUM_ALGO
    WebUi Label: Checksum algorithm
    The checksum algorithm that is used."
  ::= { mGuardCIFSIntShareEntry 10 }

-- CIFS_FILE_CHECK.CHECKSUM_SHARE reference
mGuardCIFSIntShareChksumShareRef OBJECT-TYPE
  SYNTAX OBJECT IDENTIFIER
  ACCESS read-write
  STATUS mandatory
  DESCRIPTION
    "Variable name: CIFS_FILE_CHECK.CHECKSUM_SHARE
    WebUi Label: To be stored on CIFS share
    The OID of an 'mGuardCIFSShareIndex' object that designates the share
    to be used as the checksum memory."
  ::= { mGuardCIFSIntShareEntry 4 }

-- CIFS_INTEGRITY_CERT
mGuardCIFSIntCertValue OBJECT-TYPE
  SYNTAX INTEGER {
    none(1)
  }
  ACCESS read-write
  STATUS mandatory
  DESCRIPTION
    "Variable name: CIFS_INTEGRITY_CERT
    WebUi Label: Integrity certificate (machine certificate used to sign integrity
     databases)
    This object is effective if and only if the 'mGuardCIFSIntCertRef'
    object contains the OID of this object. When this object is read, it
    always returns the value 'none'. When the value 'none' is written to
    this object, the feature to sign the integrity database is disabled."
  ::= { mGuardCIFSInt 1 }

-- CIFS_INTEGRITY_CERT reference
mGuardCIFSIntCertRef OBJECT-TYPE
  SYNTAX OBJECT IDENTIFIER
  ACCESS read-write
  STATUS mandatory
  DESCRIPTION
    "Variable name: CIFS_INTEGRITY_CERT
    WebUi Label: Integrity certificate (machine certificate used to sign integrity
     databases)
    When this object contains the OID of an 'mGuardCertsLocalIndex'
    object, the corresponding certificate is used to sign the integrity
    database. To select a local machine certificate in this manner, write
    the OID of the corresponding 'mGuardCertsLocalIndex' object to this
    object. To disable this feature, set the 'mGuardCIFSIntCertValue'
    object."
  ::= { mGuardCIFSInt 2 }

-- CIFS_INTEGRITY_EMAIL_NOTIFY
mGuardCIFSIntEMailNotification OBJECT-TYPE
  SYNTAX INTEGER {
    off(1),
    just-fails-diffs(2),
    always(3)
  }
  ACCESS read-write
  STATUS mandatory
  DESCRIPTION
    "Variable name: CIFS_INTEGRITY_EMAIL_NOTIFY
    WebUi Label: Send notifications via e-mail
    Send a notification via E-Mail: off: No E-Mail will be sent. just-
    fails-diffs: An E-Mail will be sent if a difference appears during the
    CIFS-Integrity-Check or an access error prevents the CIFS-Integrity-
    Check. always: An E-Mail will be sent after every CIFS-Integrity-
    Check."
  ::= { mGuardCIFSInt 3 }

-- CIFS_INTEGRITY_EMAIL_SUBJECT
mGuardCIFSIntEMailAddressSubj OBJECT-TYPE
  SYNTAX DisplayString
  ACCESS read-write
  STATUS mandatory
  DESCRIPTION
    "Variable name: CIFS_INTEGRITY_EMAIL_SUBJECT
    WebUi Label: Subject prefix for e-mail notifications
    Subject of the notification E-Mail."
  ::= { mGuardCIFSInt 6 }

-- CIFS_INTEGRITY_EMAIL_TO
mGuardCIFSIntEMailAddressTo OBJECT-TYPE
  SYNTAX DisplayString
  ACCESS read-write
  STATUS mandatory
  DESCRIPTION
    "Variable name: CIFS_INTEGRITY_EMAIL_TO
    WebUi Label: Target address for e-mail notifications
    E-Mail address to which the notification should be sent."
  ::= { mGuardCIFSInt 4 }


-- CIFS_SHARE table
mGuardCIFSShareTable OBJECT-TYPE
  SYNTAX SEQUENCE OF MGuardCIFSShareEntry
  ACCESS not-accessible
  STATUS mandatory
  DESCRIPTION
    "A table of CIFS_SHARE"
  ::= { mGuardCIFSShare 1 }

-- CIFS_SHARE table entry
mGuardCIFSShareEntry OBJECT-TYPE
  SYNTAX MGuardCIFSShareEntry
  ACCESS not-accessible
  STATUS mandatory
  DESCRIPTION
    "An entry of CIFS_SHARE"
  INDEX { mGuardCIFSShareIndex }
  ::= { mGuardCIFSShareTable 1 }

MGuardCIFSShareEntry ::= SEQUENCE {
  mGuardCIFSShareIndex                     INTEGER,
  mGuardCIFSShareConfigName                DisplayString,
  mGuardCIFSShareServerIP                  DisplayString,
  mGuardCIFSShareShareName                 DisplayString,
  mGuardCIFSShareAuthWorkgroup             DisplayString,
  mGuardCIFSShareAuthLogin                 DisplayString,
  mGuardCIFSServerAuthPassword             DisplayString,
  mGuardCIFSShareRowStatus                 RowStatus,
  mGuardCIFSShareNetBiosName               DisplayString,
  mGuardCIFSShareAuthType                  DisplayString
}

-- CIFS_SHARE table index
mGuardCIFSShareIndex OBJECT-TYPE
  SYNTAX INTEGER (1..2147483647)
  ACCESS not-accessible
  STATUS mandatory
  DESCRIPTION
    "Index to CIFS_SHARE"
  ::= { mGuardCIFSShareEntry 1 }

-- CIFS_SHARE row status
mGuardCIFSShareRowStatus OBJECT-TYPE
  SYNTAX RowStatus
  ACCESS read-write
  STATUS mandatory
  DESCRIPTION
    "RowStatus of CIFS_SHARE"
  ::= { mGuardCIFSShareEntry 8 }

-- CIFS_SHARE.AUTH_TYPE
mGuardCIFSShareAuthType OBJECT-TYPE
  SYNTAX DisplayString
  ACCESS read-write
  STATUS mandatory
  DESCRIPTION
    "Variable name: CIFS_SHARE.AUTH_TYPE
    WebUi Label: --
    Authentication type"
  ::= { mGuardCIFSShareEntry 11 }

-- CIFS_SHARE.NAME
mGuardCIFSShareConfigName OBJECT-TYPE
  SYNTAX DisplayString
  ACCESS read-write
  STATUS mandatory
  DESCRIPTION
    "Variable name: CIFS_SHARE.NAME
    WebUi Label: Name
    Internal configuration name of the share."
  ::= { mGuardCIFSShareEntry 2 }

-- CIFS_SHARE.SHARE_NAME
mGuardCIFSShareShareName OBJECT-TYPE
  SYNTAX DisplayString
  ACCESS read-write
  STATUS mandatory
  DESCRIPTION
    "Variable name: CIFS_SHARE.SHARE_NAME
    WebUi Label: Imported share's name
    Name of the share located at the server."
  ::= { mGuardCIFSShareEntry 4 }

-- CIFS_SHARE.WORKGROUP
mGuardCIFSShareAuthWorkgroup OBJECT-TYPE
  SYNTAX DisplayString
  ACCESS read-write
  STATUS mandatory
  DESCRIPTION
    "Variable name: CIFS_SHARE.WORKGROUP
    WebUi Label: Domain/Workgroup
    Name of the workgroup the share belongs to."
  ::= { mGuardCIFSShareEntry 5 }

-- CIFS_SHARE.NETBIOSNAME
mGuardCIFSShareNetBiosName OBJECT-TYPE
  SYNTAX DisplayString
  ACCESS read-write
  STATUS mandatory
  DESCRIPTION
    "Variable name: CIFS_SHARE.NETBIOSNAME
    WebUi Label: NetBIOS name (Windows 95/98 only)
    NetBIOS Name"
  ::= { mGuardCIFSShareEntry 9 }

-- CIFS_SHARE.FROM_SERVER
mGuardCIFSShareServerIP OBJECT-TYPE
  SYNTAX DisplayString
  ACCESS read-write
  STATUS mandatory
  DESCRIPTION
    "Variable name: CIFS_SHARE.FROM_SERVER
    WebUi Label: Address of the server
    Server address (hostname or IP) of the accessible server whose share
    should be checked."
  ::= { mGuardCIFSShareEntry 3 }

-- CIFS_SHARE.PASSWORD
mGuardCIFSServerAuthPassword OBJECT-TYPE
  SYNTAX DisplayString
  ACCESS read-write
  STATUS mandatory
  DESCRIPTION
    "Variable name: CIFS_SHARE.PASSWORD
    WebUi Label: Password
    Login password to the server"
  ::= { mGuardCIFSShareEntry 7 }

-- CIFS_SHARE.USER
mGuardCIFSShareAuthLogin OBJECT-TYPE
  SYNTAX DisplayString
  ACCESS read-write
  STATUS mandatory
  DESCRIPTION
    "Variable name: CIFS_SHARE.USER
    WebUi Label: Login
    Login to the server"
  ::= { mGuardCIFSShareEntry 6 }

-- COM_SERVER_ACCESS_RULES
mGuardSerialComServerRemoteUUID OBJECT-TYPE
  SYNTAX DisplayString
  ACCESS read-only
  STATUS mandatory
  DESCRIPTION
    "Variable name: COM_SERVER_ACCESS_RULES
    WebUi Label: COM server allowed networks
    Universally Unique Identifier (UUID, RFC 4122) used for
    mGuardSerialComServerRemoteFWRuleTable logging."
  ::= { mGuardSerialComServer 6 }


-- COM_SERVER_ACCESS_RULES table
mGuardSerialComServerRemoteFWRuleTable OBJECT-TYPE
  SYNTAX SEQUENCE OF MGuardSerialComServerRemoteFWRuleEntry
  ACCESS not-accessible
  STATUS mandatory
  DESCRIPTION
    "A table of COM_SERVER_ACCESS_RULES"
  ::= { mGuardSerialComServer 5 }

-- COM_SERVER_ACCESS_RULES table entry
mGuardSerialComServerRemoteFWRuleEntry OBJECT-TYPE
  SYNTAX MGuardSerialComServerRemoteFWRuleEntry
  ACCESS not-accessible
  STATUS mandatory
  DESCRIPTION
    "An entry of COM_SERVER_ACCESS_RULES"
  INDEX { mGuardSerialComServerFWruleIndex }
  ::= { mGuardSerialComServerRemoteFWRuleTable 1 }

MGuardSerialComServerRemoteFWRuleEntry ::= SEQUENCE {
  mGuardSerialComServerFWruleIndex         INTEGER,
  mGuardSerialComServerFWsourceIP          DisplayString,
  mGuardSerialComServerFWinterface         INTEGER,
  mGuardSerialComServerFWtarget            INTEGER,
  mGuardSerialComServerFWlog               INTEGER,
  mGuardSerialComServerFWRowStatus         RowStatus,
  mGuardSerialComServerFWcomment           DisplayString,
  mGuardSerialComServerFWfromMAC           MacAddress
}

-- COM_SERVER_ACCESS_RULES table index
mGuardSerialComServerFWruleIndex OBJECT-TYPE
  SYNTAX INTEGER (1..2147483647)
  ACCESS not-accessible
  STATUS mandatory
  DESCRIPTION
    "Index to COM_SERVER_ACCESS_RULES"
  ::= { mGuardSerialComServerRemoteFWRuleEntry 1 }

-- COM_SERVER_ACCESS_RULES row status
mGuardSerialComServerFWRowStatus OBJECT-TYPE
  SYNTAX RowStatus
  ACCESS read-write
  STATUS mandatory
  DESCRIPTION
    "RowStatus of COM_SERVER_ACCESS_RULES"
  ::= { mGuardSerialComServerRemoteFWRuleEntry 6 }

-- COM_SERVER_ACCESS_RULES.COMMENT
mGuardSerialComServerFWcomment OBJECT-TYPE
  SYNTAX DisplayString
  ACCESS read-write
  STATUS mandatory
  DESCRIPTION
    "Variable name: COM_SERVER_ACCESS_RULES.COMMENT
    WebUi Label: Comment
    Commentary or name for this rule."
  ::= { mGuardSerialComServerRemoteFWRuleEntry 7 }

-- COM_SERVER_ACCESS_RULES.LOG
mGuardSerialComServerFWlog OBJECT-TYPE
  SYNTAX INTEGER {
    yes(1),
    no(2)
  }
  ACCESS read-write
  STATUS mandatory
  DESCRIPTION
    "Variable name: COM_SERVER_ACCESS_RULES.LOG
    WebUi Label: Log
    Log packets matching this rule ?"
  ::= { mGuardSerialComServerRemoteFWRuleEntry 5 }

-- COM_SERVER_ACCESS_RULES.FROM_IP
mGuardSerialComServerFWsourceIP OBJECT-TYPE
  SYNTAX DisplayString
  ACCESS read-write
  STATUS mandatory
  DESCRIPTION
    "Variable name: COM_SERVER_ACCESS_RULES.FROM_IP
    WebUi Label: From IP
    The rule's source IP address"
  ::= { mGuardSerialComServerRemoteFWRuleEntry 2 }

-- COM_SERVER_ACCESS_RULES.INTERFACE_DEV
mGuardSerialComServerFWinterface OBJECT-TYPE
  SYNTAX INTEGER {
    extern(1),
    intern(2),
    extern2(3),
    dialin(4),
    viaipsec(5),
    dmz0(6),
    viagre(7)
  }
  ACCESS read-write
  STATUS mandatory
  DESCRIPTION
    "Variable name: COM_SERVER_ACCESS_RULES.INTERFACE_DEV
    WebUi Label: Interface
    The network interface the rule belongs to (extern/intern)."
  ::= { mGuardSerialComServerRemoteFWRuleEntry 3 }

-- COM_SERVER_ACCESS_RULES.FROM_MAC
mGuardSerialComServerFWfromMAC OBJECT-TYPE
  SYNTAX MacAddress
  ACCESS read-write
  STATUS mandatory
  DESCRIPTION
    "Variable name: COM_SERVER_ACCESS_RULES.FROM_MAC
    WebUi Label: From MAC
    The rule's source MAC address."
  ::= { mGuardSerialComServerRemoteFWRuleEntry 8 }

-- COM_SERVER_ACCESS_RULES.TARGET
mGuardSerialComServerFWtarget OBJECT-TYPE
  SYNTAX INTEGER {
    accept(1),
    reject(2),
    drop(3)
  }
  ACCESS read-write
  STATUS mandatory
  DESCRIPTION
    "Variable name: COM_SERVER_ACCESS_RULES.TARGET
    WebUi Label: Action
    The target of the rule (accept/reject/drop)."
  ::= { mGuardSerialComServerRemoteFWRuleEntry 4 }

-- COM_SERVER_PORT
mGuardSerialComServerPort OBJECT-TYPE
  SYNTAX INTEGER(1..65535)
  ACCESS read-write
  STATUS mandatory
  DESCRIPTION
    "Variable name: COM_SERVER_PORT
    WebUi Label: Local port
    Defines the listen port for the RFC2217 or raw server"
  ::= { mGuardSerialComServer 2 }

-- COM_SERVER_PREFER_VPN
mGuardSerialComServerPreferVPN OBJECT-TYPE
  SYNTAX INTEGER {
    yes(1),
    no(2)
  }
  ACCESS read-write
  STATUS mandatory
  DESCRIPTION
    "Variable name: COM_SERVER_PREFER_VPN
    WebUi Label: Via VPN
    Connect to COM server via VPN if an applicable tunnel is configured.
    Important note: If set to 'yes', all proxy settings are ignored and no
    proxy will be used even if no applicable VPN tunnel exists! The server
    will then be connected directly."
  ::= { mGuardSerialComServer 7 }

-- COM_SERVER_REMOTE_IP
mGuardSerialComServerRemoteIP OBJECT-TYPE
  SYNTAX IpAddress
  ACCESS read-write
  STATUS mandatory
  DESCRIPTION
    "Variable name: COM_SERVER_REMOTE_IP
    WebUi Label: Remote IP
    Defines the remote IP for the raw client"
  ::= { mGuardSerialComServer 3 }

-- COM_SERVER_REMOTE_PORT
mGuardSerialComServerRemotePort OBJECT-TYPE
  SYNTAX INTEGER(1..65535)
  ACCESS read-write
  STATUS mandatory
  DESCRIPTION
    "Variable name: COM_SERVER_REMOTE_PORT
    WebUi Label: Remote port
    Defines the remote port for the raw client"
  ::= { mGuardSerialComServer 4 }

-- COM_SERVER_TYPE
mGuardSerialComServerType OBJECT-TYPE
  SYNTAX INTEGER {
    off(1),
    rfc2217(2),
    rawclient(3),
    rawserver(4)
  }
  ACCESS read-write
  STATUS mandatory
  DESCRIPTION
    "Variable name: COM_SERVER_TYPE
    WebUi Label: Type
    Defines the server or client type"
  ::= { mGuardSerialComServer 1 }

-- CPU_TEMP_MAX
mGuardTResIndustrialCpuTempHiLimit OBJECT-TYPE
  SYNTAX INTEGER(-40..200)
  ACCESS read-write
  STATUS mandatory
  DESCRIPTION
    "Variable name: CPU_TEMP_MAX
    WebUi Label: CPU temperature
    Upper limit of allowed CPU temperature."
  ::= { mGuardTResIndustrialTemperature 4 }

-- CPU_TEMP_MIN
mGuardTResIndustrialCpuTempLowLimit OBJECT-TYPE
  SYNTAX INTEGER(-40..200)
  ACCESS read-write
  STATUS mandatory
  DESCRIPTION
    "Variable name: CPU_TEMP_MIN
    WebUi Label: CPU temperature
    Lower limit of allowed CPU temperature."
  ::= { mGuardTResIndustrialTemperature 5 }

-- CRL_CHECKING
mGuardCertsCRLCheck OBJECT-TYPE
  SYNTAX INTEGER {
    yes(1),
    no(2)
  }
  ACCESS read-write
  STATUS mandatory
  DESCRIPTION
    "Variable name: CRL_CHECKING
    WebUi Label: Enable CRL checking
    CRL Check: yes/no"
  ::= { mGuardCertsCRL 2 }

-- CRL_PULL_INTERVAL
mGuardCertsCRLPullInterval OBJECT-TYPE
  SYNTAX INTEGER
  ACCESS read-write
  STATUS mandatory
  DESCRIPTION
    "Variable name: CRL_PULL_INTERVAL
    WebUi Label: CRL download interval
    CRL download interval in seconds."
  ::= { mGuardCertsCRL 1 }


-- CRL_STORE table
mGuardCertsCRLTable OBJECT-TYPE
  SYNTAX SEQUENCE OF MGuardCertsCRLEntry
  ACCESS not-accessible
  STATUS mandatory
  DESCRIPTION
    "A table of CRL_STORE"
  ::= { mGuardCertsCRL 3 }

-- CRL_STORE table entry
mGuardCertsCRLEntry OBJECT-TYPE
  SYNTAX MGuardCertsCRLEntry
  ACCESS not-accessible
  STATUS mandatory
  DESCRIPTION
    "An entry of CRL_STORE"
  INDEX { mGuardCertsCRLIndex }
  ::= { mGuardCertsCRLTable 1 }

MGuardCertsCRLEntry ::= SEQUENCE {
  mGuardCertsCRLIndex                      INTEGER,
  mGuardCertsCRLURI                        DisplayString,
  mGuardCertsCRLRowStatus                  RowStatus,
  mGuardCertsCRLFile                       DisplayString,
  mGuardCertsCRLPreferVPN                  INTEGER
}

-- CRL_STORE table index
mGuardCertsCRLIndex OBJECT-TYPE
  SYNTAX INTEGER (1..2147483647)
  ACCESS not-accessible
  STATUS mandatory
  DESCRIPTION
    "Index to CRL_STORE"
  ::= { mGuardCertsCRLEntry 1 }

-- CRL_STORE row status
mGuardCertsCRLRowStatus OBJECT-TYPE
  SYNTAX RowStatus
  ACCESS read-write
  STATUS mandatory
  DESCRIPTION
    "RowStatus of CRL_STORE"
  ::= { mGuardCertsCRLEntry 20 }

-- CRL_STORE.PREFER_VPN
mGuardCertsCRLPreferVPN OBJECT-TYPE
  SYNTAX INTEGER {
    yes(1),
    no(2)
  }
  ACCESS read-write
  STATUS mandatory
  DESCRIPTION
    "Variable name: CRL_STORE.PREFER_VPN
    WebUi Label: Via VPN
    Download this CRL from URI via VPN if an applicable tunnel is
    configured. Important note: If set to 'yes', all proxy settings are
    ignored and no proxy will be used even if no applicable VPN tunnel
    exists! The server will then be connected directly."
  ::= { mGuardCertsCRLEntry 22 }

-- CRL_STORE.CRL_FILE
mGuardCertsCRLFile OBJECT-TYPE
  SYNTAX DisplayString
  ACCESS read-write
  STATUS mandatory
  DESCRIPTION
    "Variable name: CRL_STORE.CRL_FILE
    WebUi Label: Upload
    Name of the CRL File"
  ::= { mGuardCertsCRLEntry 21 }

-- CRL_STORE.URI
mGuardCertsCRLURI OBJECT-TYPE
  SYNTAX DisplayString
  ACCESS read-write
  STATUS mandatory
  DESCRIPTION
    "Variable name: CRL_STORE.URI
    WebUi Label: URL
    An URI from which the CRL will be loaded."
  ::= { mGuardCertsCRLEntry 2 }

-- DEFAULT_GW
mGuardRouterExternStaticGateway OBJECT-TYPE
  SYNTAX IpAddress
  ACCESS read-write
  STATUS mandatory
  DESCRIPTION
    "Variable name: DEFAULT_GW
    WebUi Label: IP of default gateway
    The (extern) default gateway of this device in router mode (when
    statically configured)."
  ::= { mGuardRouterExternStatic 3 }

-- DHCP_DMZ_BROADCAST
mGuardDHCPDmzBroadcast OBJECT-TYPE
  SYNTAX IpAddress
  ACCESS read-write
  STATUS mandatory
  DESCRIPTION
    "Variable name: DHCP_DMZ_BROADCAST
    WebUi Label: Broadcast address
    Broadcast address provided by the built-in DHCP server."
  ::= { mGuardDHCPDmz 9 }

-- DHCP_DMZ_DNS
mGuardDHCPDmzDnsServer OBJECT-TYPE
  SYNTAX IpAddress
  ACCESS read-write
  STATUS mandatory
  DESCRIPTION
    "Variable name: DHCP_DMZ_DNS
    WebUi Label: DNS server
    DNS Server provided by the built-in DHCP server."
  ::= { mGuardDHCPDmz 7 }

-- DHCP_DMZ_ENABLE
mGuardDHCPDmzStart OBJECT-TYPE
  SYNTAX INTEGER {
    yes(1),
    no(2)
  }
  ACCESS read-write
  STATUS mandatory
  DESCRIPTION
    "Variable name: DHCP_DMZ_ENABLE
    WebUi Label: Enable DHCP server on the DMZ port
    Enable the internal DHCP/DHCP Server ?"
  ::= { mGuardDHCPDmz 1 }

-- DHCP_DMZ_END
mGuardDHCPDmzRangeEnd OBJECT-TYPE
  SYNTAX IpAddress
  ACCESS read-write
  STATUS mandatory
  DESCRIPTION
    "Variable name: DHCP_DMZ_END
    WebUi Label: DHCP range end
    End of IP range provided by the built-in DHCP Server for the DMZ
    network."
  ::= { mGuardDHCPDmz 4 }

-- DHCP_DMZ_GW
mGuardDHCPDmzGateway OBJECT-TYPE
  SYNTAX IpAddress
  ACCESS read-write
  STATUS mandatory
  DESCRIPTION
    "Variable name: DHCP_DMZ_GW
    WebUi Label: Default gateway
    Default gateway provided by the built-in DHCP Server for the DMZ
    network."
  ::= { mGuardDHCPDmz 6 }

-- DHCP_DMZ_LEASE_TIME
mGuardDHCPDmzLeaseTime OBJECT-TYPE
  SYNTAX INTEGER
  ACCESS read-write
  STATUS mandatory
  DESCRIPTION
    "Variable name: DHCP_DMZ_LEASE_TIME
    WebUi Label: DHCP lease time
    Lifetime for DHCP Leases"
  ::= { mGuardDHCPDmz 11 }

-- DHCP_DMZ_MASK
mGuardDHCPDmzNetmask OBJECT-TYPE
  SYNTAX IpAddress
  ACCESS read-write
  STATUS mandatory
  DESCRIPTION
    "Variable name: DHCP_DMZ_MASK
    WebUi Label: Local netmask
    Netmask provided by the built-in DHCP Server for the DMZ network."
  ::= { mGuardDHCPDmz 5 }

-- DHCP_DMZ_POOL
mGuardDHCPDmzPoolEnable OBJECT-TYPE
  SYNTAX INTEGER {
    yes(1),
    no(2)
  }
  ACCESS read-write
  STATUS mandatory
  DESCRIPTION
    "Variable name: DHCP_DMZ_POOL
    WebUi Label: Enable dynamic IP address pool
    Enable the dynamic DHCP Pool ?"
  ::= { mGuardDHCPDmz 2 }

-- DHCP_DMZ_START
mGuardDHCPDmzRangeStart OBJECT-TYPE
  SYNTAX IpAddress
  ACCESS read-write
  STATUS mandatory
  DESCRIPTION
    "Variable name: DHCP_DMZ_START
    WebUi Label: DHCP range start
    Start of IP range provided by the built-in DHCP Server for the DMZ
    network."
  ::= { mGuardDHCPDmz 3 }

-- DHCP_DMZ_WINS
mGuardDHCPDmzWINS OBJECT-TYPE
  SYNTAX IpAddress
  ACCESS read-write
  STATUS mandatory
  DESCRIPTION
    "Variable name: DHCP_DMZ_WINS
    WebUi Label: WINS server
    WINS provided by the built-in DHCP Server for the DMZ network."
  ::= { mGuardDHCPDmz 10 }

-- DHCP_EXT_BROADCAST
mGuardDHCPExtBroadcast OBJECT-TYPE
  SYNTAX IpAddress
  ACCESS read-write
  STATUS mandatory
  DESCRIPTION
    "Variable name: DHCP_EXT_BROADCAST
    WebUi Label: Broadcast address
    Broadcast address provided by the built-in DHCP server."
  ::= { mGuardDHCPExt 9 }

-- DHCP_EXT_DNS
mGuardDHCPExtDnsServer OBJECT-TYPE
  SYNTAX IpAddress
  ACCESS read-write
  STATUS mandatory
  DESCRIPTION
    "Variable name: DHCP_EXT_DNS
    WebUi Label: DNS server
    DNS Server provided by the built-in DHCP server."
  ::= { mGuardDHCPExt 7 }

-- DHCP_EXT_ENABLE
mGuardDHCPExtStart OBJECT-TYPE
  SYNTAX INTEGER {
    enabled(1),
    disabled(2),
    enabled-relay(3)
  }
  ACCESS read-write
  STATUS mandatory
  DESCRIPTION
    "Variable name: DHCP_EXT_ENABLE
    WebUi Label: DHCP mode
    Enable the external DHCP/DHCP Relay Server ?"
  ::= { mGuardDHCPExt 1 }

-- DHCP_EXT_END
mGuardDHCPExtRangeEnd OBJECT-TYPE
  SYNTAX IpAddress
  ACCESS read-write
  STATUS mandatory
  DESCRIPTION
    "Variable name: DHCP_EXT_END
    WebUi Label: DHCP range end
    End of IP range provided by the built-in DHCP Server for the external
    network."
  ::= { mGuardDHCPExt 4 }

-- DHCP_EXT_GW
mGuardDHCPExtGateway OBJECT-TYPE
  SYNTAX IpAddress
  ACCESS read-write
  STATUS mandatory
  DESCRIPTION
    "Variable name: DHCP_EXT_GW
    WebUi Label: Default gateway
    Default gateway provided by the built-in DHCP Server for the external
    network."
  ::= { mGuardDHCPExt 6 }

-- DHCP_EXT_LEASE_TIME
mGuardDHCPExtLeaseTime OBJECT-TYPE
  SYNTAX INTEGER
  ACCESS read-write
  STATUS mandatory
  DESCRIPTION
    "Variable name: DHCP_EXT_LEASE_TIME
    WebUi Label: DHCP lease time
    Lifetime for DHCP Leases"
  ::= { mGuardDHCPExt 11 }

-- DHCP_EXT_MASK
mGuardDHCPExtNetmask OBJECT-TYPE
  SYNTAX IpAddress
  ACCESS read-write
  STATUS mandatory
  DESCRIPTION
    "Variable name: DHCP_EXT_MASK
    WebUi Label: Local netmask
    Netmask provided by the built-in DHCP Server for the external network."
  ::= { mGuardDHCPExt 5 }

-- DHCP_EXT_POOL
mGuardDHCPExtPoolEnable OBJECT-TYPE
  SYNTAX INTEGER {
    yes(1),
    no(2)
  }
  ACCESS read-write
  STATUS mandatory
  DESCRIPTION
    "Variable name: DHCP_EXT_POOL
    WebUi Label: Enable dynamic IP address pool
    Enable the dynamic DHCP Pool ?"
  ::= { mGuardDHCPExt 2 }

-- DHCP_EXT_START
mGuardDHCPExtRangeStart OBJECT-TYPE
  SYNTAX IpAddress
  ACCESS read-write
  STATUS mandatory
  DESCRIPTION
    "Variable name: DHCP_EXT_START
    WebUi Label: DHCP range start
    Start of IP range provided by the built-in DHCP Server for the
    external network."
  ::= { mGuardDHCPExt 3 }

-- DHCP_EXT_WINS
mGuardDHCPExtWINS OBJECT-TYPE
  SYNTAX IpAddress
  ACCESS read-write
  STATUS mandatory
  DESCRIPTION
    "Variable name: DHCP_EXT_WINS
    WebUi Label: WINS server
    WINS provided by the built-in DHCP Server for the external network."
  ::= { mGuardDHCPExt 10 }

-- DHCP_INT_BROADCAST
mGuardDHCPIntBroadcast OBJECT-TYPE
  SYNTAX IpAddress
  ACCESS read-write
  STATUS mandatory
  DESCRIPTION
    "Variable name: DHCP_INT_BROADCAST
    WebUi Label: Broadcast address
    Broadcast address provided by the built-in DHCP server."
  ::= { mGuardDHCPInt 9 }

-- DHCP_INT_DNS
mGuardDHCPIntDnsServer OBJECT-TYPE
  SYNTAX IpAddress
  ACCESS read-write
  STATUS mandatory
  DESCRIPTION
    "Variable name: DHCP_INT_DNS
    WebUi Label: DNS server
    DNS Server provided by the built-in DHCP server."
  ::= { mGuardDHCPInt 7 }

-- DHCP_INT_ENABLE
mGuardDHCPIntStart OBJECT-TYPE
  SYNTAX INTEGER {
    enabled(1),
    disabled(2),
    enabled-relay(3)
  }
  ACCESS read-write
  STATUS mandatory
  DESCRIPTION
    "Variable name: DHCP_INT_ENABLE
    WebUi Label: DHCP mode
    Enable the internal DHCP/DHCP Relay Server ?"
  ::= { mGuardDHCPInt 1 }

-- DHCP_INT_END
mGuardDHCPIntRangeEnd OBJECT-TYPE
  SYNTAX IpAddress
  ACCESS read-write
  STATUS mandatory
  DESCRIPTION
    "Variable name: DHCP_INT_END
    WebUi Label: DHCP range end
    End of IP range provided by the built-in DHCP Server for the internal
    network."
  ::= { mGuardDHCPInt 4 }

-- DHCP_INT_GW
mGuardDHCPIntGateway OBJECT-TYPE
  SYNTAX IpAddress
  ACCESS read-write
  STATUS mandatory
  DESCRIPTION
    "Variable name: DHCP_INT_GW
    WebUi Label: Default gateway
    Default gateway provided by the built-in DHCP Server for the internal
    network."
  ::= { mGuardDHCPInt 6 }

-- DHCP_INT_LEASE_TIME
mGuardDHCPIntLeaseTime OBJECT-TYPE
  SYNTAX INTEGER
  ACCESS read-write
  STATUS mandatory
  DESCRIPTION
    "Variable name: DHCP_INT_LEASE_TIME
    WebUi Label: DHCP lease time
    Lifetime for DHCP Leases"
  ::= { mGuardDHCPInt 11 }

-- DHCP_INT_MASK
mGuardDHCPIntNetmask OBJECT-TYPE
  SYNTAX IpAddress
  ACCESS read-write
  STATUS mandatory
  DESCRIPTION
    "Variable name: DHCP_INT_MASK
    WebUi Label: Local netmask
    Netmask provided by the built-in DHCP Server for the internal network."
  ::= { mGuardDHCPInt 5 }

-- DHCP_INT_POOL
mGuardDHCPIntPoolEnable OBJECT-TYPE
  SYNTAX INTEGER {
    yes(1),
    no(2)
  }
  ACCESS read-write
  STATUS mandatory
  DESCRIPTION
    "Variable name: DHCP_INT_POOL
    WebUi Label: Enable dynamic IP address pool
    Enable the dynamic DHCP Pool ?"
  ::= { mGuardDHCPInt 2 }

-- DHCP_INT_START
mGuardDHCPIntRangeStart OBJECT-TYPE
  SYNTAX IpAddress
  ACCESS read-write
  STATUS mandatory
  DESCRIPTION
    "Variable name: DHCP_INT_START
    WebUi Label: DHCP range start
    Start of IP range provided by the built-in DHCP Server for the
    internal network."
  ::= { mGuardDHCPInt 3 }

-- DHCP_INT_WINS
mGuardDHCPIntWINS OBJECT-TYPE
  SYNTAX IpAddress
  ACCESS read-write
  STATUS mandatory
  DESCRIPTION
    "Variable name: DHCP_INT_WINS
    WebUi Label: WINS server
    WINS provided by the built-in DHCP Server for the internal network."
  ::= { mGuardDHCPInt 10 }

-- DHCP_RELAY_EXT_APPEND_AGENT_INFORMATION
mGuardDHCPExtRelayAppend OBJECT-TYPE
  SYNTAX INTEGER {
    yes(1),
    no(2)
  }
  ACCESS read-write
  STATUS mandatory
  DESCRIPTION
    "Variable name: DHCP_RELAY_EXT_APPEND_AGENT_INFORMATION
    WebUi Label: Append relay agent information (option 82)
    Whether to append DHCP Relay Agent Information."
  ::= { mGuardDHCPExt 52 }

-- DHCP_RELAY_EXT_APPEND_LIMIT
mGuardDHCPExtRelayAppendLimit OBJECT-TYPE
  SYNTAX INTEGER
  ACCESS read-write
  STATUS mandatory
  DESCRIPTION
    "Variable name: DHCP_RELAY_EXT_APPEND_LIMIT
    WebUi Label: DHCP relay append limit
    When appending DHCP Relay Agent Information would exceed this limit,
    it is not appended."
  ::= { mGuardDHCPExt 53 }

-- DHCP_RELAY_EXT_CIRCUIT_INFO
mGuardDHCPExtRelayCircuitInfo OBJECT-TYPE
  SYNTAX INTEGER {
    none(1),
    if-idx(2),
    if-name(3),
    if-mac(4),
    if-ip(5),
    sysname(6),
    text(7),
    if-prefixed-ip(8),
    rs2(9)
  }
  ACCESS read-write
  STATUS mandatory
  DESCRIPTION
    "Variable name: DHCP_RELAY_EXT_CIRCUIT_INFO
    WebUi Label: Circuit ID
    What to append as Circuit ID: none: no Circuit ID if-idx: the system
    interface index (1 octet) if-name: the systems interface name (ascii)
    if-mac: the MAC address (6 octets) if-ip: the IP address (4 octets)
    sysname: the systems hostname text: a text defined in
    mGuardDHCPExtRelayCircuitText.0 if-prefixed-ip: prefix IP with 0xA1
    Sub Remote ID (2+4 octets) rs2: Hirschmann RS2 Sub Circuit Information"
  ::= { mGuardDHCPExt 54 }

-- DHCP_RELAY_EXT_CIRCUIT_TEXT
mGuardDHCPExtRelayCircuitText OBJECT-TYPE
  SYNTAX DisplayString
  ACCESS read-write
  STATUS mandatory
  DESCRIPTION
    "Variable name: DHCP_RELAY_EXT_CIRCUIT_TEXT
    WebUi Label: Circuit ID
    Text in case mGuardDHCPExtRelayCircuitInfo.0 is set to text(7)."
  ::= { mGuardDHCPExt 55 }

-- DHCP_RELAY_EXT_MAXHOP
mGuardDHCPExtRelayMaxHop OBJECT-TYPE
  SYNTAX INTEGER
  ACCESS read-write
  STATUS mandatory
  DESCRIPTION
    "Variable name: DHCP_RELAY_EXT_MAXHOP
    WebUi Label: Max. hop count
    Maximal number of Hops when relaying."
  ::= { mGuardDHCPExt 51 }

-- DHCP_RELAY_EXT_REMOTE_INFO
mGuardDHCPExtRelayRemoteInfo OBJECT-TYPE
  SYNTAX INTEGER {
    none(1),
    if-idx(2),
    if-name(3),
    if-mac(4),
    if-ip(5),
    sysname(6),
    text(7),
    if-prefixed-ip(8),
    rs2(9)
  }
  ACCESS read-write
  STATUS mandatory
  DESCRIPTION
    "Variable name: DHCP_RELAY_EXT_REMOTE_INFO
    WebUi Label: Remote ID
    What to append as Remote ID: none: no Circuit ID if-idx: the system
    interface index (1 octet) if-name: the systems interface name (ascii)
    if-mac: the MAC address (6 octets) if-ip: the IP address (4 octets)
    sysname: the systems hostname text: a text defined in
    mGuardDHCPExtRelayRemoteText.0 if-prefixed-ip: prefix IP with 0xA1 Sub
    Remote ID (2+4 octets) rs2: Hirschmann RS2 Sub Circuit Information"
  ::= { mGuardDHCPExt 56 }

-- DHCP_RELAY_EXT_REMOTE_TEXT
mGuardDHCPExtRelayRemoteText OBJECT-TYPE
  SYNTAX DisplayString
  ACCESS read-write
  STATUS mandatory
  DESCRIPTION
    "Variable name: DHCP_RELAY_EXT_REMOTE_TEXT
    WebUi Label: Remote ID
    Text in case mGuardDHCPExtRelayRemoteInfo.0 is set to text(7)."
  ::= { mGuardDHCPExt 57 }


-- DHCP_RELAY_EXT_SERVER table
mGuardDHCPExtRelayServerTable OBJECT-TYPE
  SYNTAX SEQUENCE OF MGuardDHCPExtRelayServerEntry
  ACCESS not-accessible
  STATUS mandatory
  DESCRIPTION
    "A table of DHCP_RELAY_EXT_SERVER"
  ::= { mGuardDHCPExt 50 }

-- DHCP_RELAY_EXT_SERVER table entry
mGuardDHCPExtRelayServerEntry OBJECT-TYPE
  SYNTAX MGuardDHCPExtRelayServerEntry
  ACCESS not-accessible
  STATUS mandatory
  DESCRIPTION
    "An entry of DHCP_RELAY_EXT_SERVER"
  INDEX { mGuardDHCPExtRelayServerIndex }
  ::= { mGuardDHCPExtRelayServerTable 1 }

MGuardDHCPExtRelayServerEntry ::= SEQUENCE {
  mGuardDHCPExtRelayServerIndex            INTEGER,
  mGuardDHCPExtRelayServerIP               IpAddress,
  mGuardDHCPExtRelayRowStatus              RowStatus
}

-- DHCP_RELAY_EXT_SERVER table index
mGuardDHCPExtRelayServerIndex OBJECT-TYPE
  SYNTAX INTEGER (1..2147483647)
  ACCESS not-accessible
  STATUS mandatory
  DESCRIPTION
    "Index to DHCP_RELAY_EXT_SERVER"
  ::= { mGuardDHCPExtRelayServerEntry 1 }

-- DHCP_RELAY_EXT_SERVER row status
mGuardDHCPExtRelayRowStatus OBJECT-TYPE
  SYNTAX RowStatus
  ACCESS read-write
  STATUS mandatory
  DESCRIPTION
    "RowStatus of DHCP_RELAY_EXT_SERVER"
  ::= { mGuardDHCPExtRelayServerEntry 10 }

-- DHCP_RELAY_EXT_SERVER.IP
mGuardDHCPExtRelayServerIP OBJECT-TYPE
  SYNTAX IpAddress
  ACCESS read-write
  STATUS mandatory
  DESCRIPTION
    "Variable name: DHCP_RELAY_EXT_SERVER.IP
    WebUi Label: IP
    The allocated IP address"
  ::= { mGuardDHCPExtRelayServerEntry 2 }

-- DHCP_RELAY_INT_APPEND_AGENT_INFORMATION
mGuardDHCPIntRelayAppend OBJECT-TYPE
  SYNTAX INTEGER {
    yes(1),
    no(2)
  }
  ACCESS read-write
  STATUS mandatory
  DESCRIPTION
    "Variable name: DHCP_RELAY_INT_APPEND_AGENT_INFORMATION
    WebUi Label: Append relay agent information (option 82)
    Whether to append DHCP Relay Agent Information."
  ::= { mGuardDHCPInt 52 }

-- DHCP_RELAY_INT_APPEND_LIMIT
mGuardDHCPIntRelayAppendLimit OBJECT-TYPE
  SYNTAX INTEGER
  ACCESS read-write
  STATUS mandatory
  DESCRIPTION
    "Variable name: DHCP_RELAY_INT_APPEND_LIMIT
    WebUi Label: DHCP relay append limit
    When appending DHCP Relay Agent Information would exceed this limit,
    it is not appended."
  ::= { mGuardDHCPInt 53 }

-- DHCP_RELAY_INT_CIRCUIT_INFO
mGuardDHCPIntRelayCircuitInfo OBJECT-TYPE
  SYNTAX INTEGER {
    none(1),
    if-idx(2),
    if-name(3),
    if-mac(4),
    if-ip(5),
    sysname(6),
    text(7),
    if-prefixed-ip(8),
    rs2(9)
  }
  ACCESS read-write
  STATUS mandatory
  DESCRIPTION
    "Variable name: DHCP_RELAY_INT_CIRCUIT_INFO
    WebUi Label: Circuit ID
    What to append as Circuit ID: none: no Circuit ID if-idx: the system
    interface index (1 octet) if-name: the systems interface name (ascii)
    if-mac: the MAC address (6 octets) if-ip: the IP address (4 octets)
    sysname: the systems hostname text: a text defined in
    mGuardDHCPIntRelayCircuitText.0 if-prefixed-ip: prefix IP with 0xA1
    Sub Remote ID (2+4 octets) rs2: Hirschmann RS2 Sub Circuit Information"
  ::= { mGuardDHCPInt 54 }

-- DHCP_RELAY_INT_CIRCUIT_TEXT
mGuardDHCPIntRelayCircuitText OBJECT-TYPE
  SYNTAX DisplayString
  ACCESS read-write
  STATUS mandatory
  DESCRIPTION
    "Variable name: DHCP_RELAY_INT_CIRCUIT_TEXT
    WebUi Label: Circuit ID
    Text in case mGuardDHCPIntRelayCircuitInfo.0 is set to text(7)."
  ::= { mGuardDHCPInt 55 }

-- DHCP_RELAY_INT_MAXHOP
mGuardDHCPIntRelayMaxHop OBJECT-TYPE
  SYNTAX INTEGER
  ACCESS read-write
  STATUS mandatory
  DESCRIPTION
    "Variable name: DHCP_RELAY_INT_MAXHOP
    WebUi Label: Max. hop count
    Maximal number of Hops when relaying."
  ::= { mGuardDHCPInt 51 }

-- DHCP_RELAY_INT_REMOTE_INFO
mGuardDHCPIntRelayRemoteInfo OBJECT-TYPE
  SYNTAX INTEGER {
    none(1),
    if-idx(2),
    if-name(3),
    if-mac(4),
    if-ip(5),
    sysname(6),
    text(7),
    if-prefixed-ip(8),
    rs2(9)
  }
  ACCESS read-write
  STATUS mandatory
  DESCRIPTION
    "Variable name: DHCP_RELAY_INT_REMOTE_INFO
    WebUi Label: Remote ID
    What to append as Remote ID: none: no Circuit ID if-idx: the system
    interface index (1 octet) if-name: the systems interface name (ascii)
    if-mac: the MAC address (6 octets) if-ip: the IP address (4 octets)
    sysname: the systems hostname text: a text defined in
    mGuardDHCPIntRelayRemoteText.0 if-prefixed-ip: prefix IP with 0xA1 Sub
    Remote ID (2+4 octets) rs2: Hirschmann RS2 Sub Circuit Information"
  ::= { mGuardDHCPInt 56 }

-- DHCP_RELAY_INT_REMOTE_TEXT
mGuardDHCPIntRelayRemoteText OBJECT-TYPE
  SYNTAX DisplayString
  ACCESS read-write
  STATUS mandatory
  DESCRIPTION
    "Variable name: DHCP_RELAY_INT_REMOTE_TEXT
    WebUi Label: Remote ID
    Text in case mGuardDHCPIntRelayRemoteInfo.0 is set to text(7)."
  ::= { mGuardDHCPInt 57 }


-- DHCP_RELAY_INT_SERVER table
mGuardDHCPIntRelayServerTable OBJECT-TYPE
  SYNTAX SEQUENCE OF MGuardDHCPIntRelayServerEntry
  ACCESS not-accessible
  STATUS mandatory
  DESCRIPTION
    "A table of DHCP_RELAY_INT_SERVER"
  ::= { mGuardDHCPInt 50 }

-- DHCP_RELAY_INT_SERVER table entry
mGuardDHCPIntRelayServerEntry OBJECT-TYPE
  SYNTAX MGuardDHCPIntRelayServerEntry
  ACCESS not-accessible
  STATUS mandatory
  DESCRIPTION
    "An entry of DHCP_RELAY_INT_SERVER"
  INDEX { mGuardDHCPIntRelayServerIndex }
  ::= { mGuardDHCPIntRelayServerTable 1 }

MGuardDHCPIntRelayServerEntry ::= SEQUENCE {
  mGuardDHCPIntRelayServerIndex            INTEGER,
  mGuardDHCPIntRelayServerIP               IpAddress,
  mGuardDHCPIntRelayRowStatus              RowStatus
}

-- DHCP_RELAY_INT_SERVER table index
mGuardDHCPIntRelayServerIndex OBJECT-TYPE
  SYNTAX INTEGER (1..2147483647)
  ACCESS not-accessible
  STATUS mandatory
  DESCRIPTION
    "Index to DHCP_RELAY_INT_SERVER"
  ::= { mGuardDHCPIntRelayServerEntry 1 }

-- DHCP_RELAY_INT_SERVER row status
mGuardDHCPIntRelayRowStatus OBJECT-TYPE
  SYNTAX RowStatus
  ACCESS read-write
  STATUS mandatory
  DESCRIPTION
    "RowStatus of DHCP_RELAY_INT_SERVER"
  ::= { mGuardDHCPIntRelayServerEntry 10 }

-- DHCP_RELAY_INT_SERVER.IP
mGuardDHCPIntRelayServerIP OBJECT-TYPE
  SYNTAX IpAddress
  ACCESS read-write
  STATUS mandatory
  DESCRIPTION
    "Variable name: DHCP_RELAY_INT_SERVER.IP
    WebUi Label: IP
    The allocated IP address"
  ::= { mGuardDHCPIntRelayServerEntry 2 }


-- DHCP_STATIC_DMZ table
mGuardDHCPDmzStaticTable OBJECT-TYPE
  SYNTAX SEQUENCE OF MGuardDHCPDmzStaticEntry
  ACCESS not-accessible
  STATUS mandatory
  DESCRIPTION
    "A table of DHCP_STATIC_DMZ"
  ::= { mGuardDHCPDmz 8 }

-- DHCP_STATIC_DMZ table entry
mGuardDHCPDmzStaticEntry OBJECT-TYPE
  SYNTAX MGuardDHCPDmzStaticEntry
  ACCESS not-accessible
  STATUS mandatory
  DESCRIPTION
    "An entry of DHCP_STATIC_DMZ"
  INDEX { mGuardDHCPDmzStaticIndex }
  ::= { mGuardDHCPDmzStaticTable 1 }

MGuardDHCPDmzStaticEntry ::= SEQUENCE {
  mGuardDHCPDmzStaticIndex                 INTEGER,
  mGuardDHCPDmzStaticMAC                   MacAddress,
  mGuardDHCPDmzStaticIP                    IpAddress,
  mGuardDHCPDmzStaticRowStatus             RowStatus,
  mGuardDHCPDmzStaticComment               DisplayString
}

-- DHCP_STATIC_DMZ table index
mGuardDHCPDmzStaticIndex OBJECT-TYPE
  SYNTAX INTEGER (1..2147483647)
  ACCESS not-accessible
  STATUS mandatory
  DESCRIPTION
    "Index to DHCP_STATIC_DMZ"
  ::= { mGuardDHCPDmzStaticEntry 1 }

-- DHCP_STATIC_DMZ row status
mGuardDHCPDmzStaticRowStatus OBJECT-TYPE
  SYNTAX RowStatus
  ACCESS read-write
  STATUS mandatory
  DESCRIPTION
    "RowStatus of DHCP_STATIC_DMZ"
  ::= { mGuardDHCPDmzStaticEntry 4 }

-- DHCP_STATIC_DMZ.COMMENT
mGuardDHCPDmzStaticComment OBJECT-TYPE
  SYNTAX DisplayString
  ACCESS read-write
  STATUS mandatory
  DESCRIPTION
    "Variable name: DHCP_STATIC_DMZ.COMMENT
    WebUi Label: Comment
    Comment"
  ::= { mGuardDHCPDmzStaticEntry 5 }

-- DHCP_STATIC_DMZ.IP
mGuardDHCPDmzStaticIP OBJECT-TYPE
  SYNTAX IpAddress
  ACCESS read-write
  STATUS mandatory
  DESCRIPTION
    "Variable name: DHCP_STATIC_DMZ.IP
    WebUi Label: Client IP address
    The allocated IP address"
  ::= { mGuardDHCPDmzStaticEntry 3 }

-- DHCP_STATIC_DMZ.MAC
mGuardDHCPDmzStaticMAC OBJECT-TYPE
  SYNTAX MacAddress
  ACCESS read-write
  STATUS mandatory
  DESCRIPTION
    "Variable name: DHCP_STATIC_DMZ.MAC
    WebUi Label: Client MAC address
    The client's MAC address"
  ::= { mGuardDHCPDmzStaticEntry 2 }


-- DHCP_STATIC_EXT table
mGuardDHCPExtStaticTable OBJECT-TYPE
  SYNTAX SEQUENCE OF MGuardDHCPExtStaticEntry
  ACCESS not-accessible
  STATUS mandatory
  DESCRIPTION
    "A table of DHCP_STATIC_EXT"
  ::= { mGuardDHCPExt 8 }

-- DHCP_STATIC_EXT table entry
mGuardDHCPExtStaticEntry OBJECT-TYPE
  SYNTAX MGuardDHCPExtStaticEntry
  ACCESS not-accessible
  STATUS mandatory
  DESCRIPTION
    "An entry of DHCP_STATIC_EXT"
  INDEX { mGuardDHCPExtStaticIndex }
  ::= { mGuardDHCPExtStaticTable 1 }

MGuardDHCPExtStaticEntry ::= SEQUENCE {
  mGuardDHCPExtStaticIndex                 INTEGER,
  mGuardDHCPExtStaticMAC                   MacAddress,
  mGuardDHCPExtStaticIP                    IpAddress,
  mGuardDHCPExtStaticRowStatus             RowStatus,
  mGuardDHCPExtStaticComment               DisplayString
}

-- DHCP_STATIC_EXT table index
mGuardDHCPExtStaticIndex OBJECT-TYPE
  SYNTAX INTEGER (1..2147483647)
  ACCESS not-accessible
  STATUS mandatory
  DESCRIPTION
    "Index to DHCP_STATIC_EXT"
  ::= { mGuardDHCPExtStaticEntry 1 }

-- DHCP_STATIC_EXT row status
mGuardDHCPExtStaticRowStatus OBJECT-TYPE
  SYNTAX RowStatus
  ACCESS read-write
  STATUS mandatory
  DESCRIPTION
    "RowStatus of DHCP_STATIC_EXT"
  ::= { mGuardDHCPExtStaticEntry 4 }

-- DHCP_STATIC_EXT.COMMENT
mGuardDHCPExtStaticComment OBJECT-TYPE
  SYNTAX DisplayString
  ACCESS read-write
  STATUS mandatory
  DESCRIPTION
    "Variable name: DHCP_STATIC_EXT.COMMENT
    WebUi Label: Comment
    Comment"
  ::= { mGuardDHCPExtStaticEntry 5 }

-- DHCP_STATIC_EXT.IP
mGuardDHCPExtStaticIP OBJECT-TYPE
  SYNTAX IpAddress
  ACCESS read-write
  STATUS mandatory
  DESCRIPTION
    "Variable name: DHCP_STATIC_EXT.IP
    WebUi Label: Client IP address
    The allocated IP address"
  ::= { mGuardDHCPExtStaticEntry 3 }

-- DHCP_STATIC_EXT.MAC
mGuardDHCPExtStaticMAC OBJECT-TYPE
  SYNTAX MacAddress
  ACCESS read-write
  STATUS mandatory
  DESCRIPTION
    "Variable name: DHCP_STATIC_EXT.MAC
    WebUi Label: Client MAC address
    The client's MAC address"
  ::= { mGuardDHCPExtStaticEntry 2 }


-- DHCP_STATIC_INT table
mGuardDHCPIntStaticTable OBJECT-TYPE
  SYNTAX SEQUENCE OF MGuardDHCPIntStaticEntry
  ACCESS not-accessible
  STATUS mandatory
  DESCRIPTION
    "A table of DHCP_STATIC_INT"
  ::= { mGuardDHCPInt 8 }

-- DHCP_STATIC_INT table entry
mGuardDHCPIntStaticEntry OBJECT-TYPE
  SYNTAX MGuardDHCPIntStaticEntry
  ACCESS not-accessible
  STATUS mandatory
  DESCRIPTION
    "An entry of DHCP_STATIC_INT"
  INDEX { mGuardDHCPIntStaticIndex }
  ::= { mGuardDHCPIntStaticTable 1 }

MGuardDHCPIntStaticEntry ::= SEQUENCE {
  mGuardDHCPIntStaticIndex                 INTEGER,
  mGuardDHCPIntStaticMAC                   MacAddress,
  mGuardDHCPIntStaticIP                    IpAddress,
  mGuardDHCPIntStaticRowStatus             RowStatus,
  mGuardDHCPIntStaticComment               DisplayString
}

-- DHCP_STATIC_INT table index
mGuardDHCPIntStaticIndex OBJECT-TYPE
  SYNTAX INTEGER (1..2147483647)
  ACCESS not-accessible
  STATUS mandatory
  DESCRIPTION
    "Index to DHCP_STATIC_INT"
  ::= { mGuardDHCPIntStaticEntry 1 }

-- DHCP_STATIC_INT row status
mGuardDHCPIntStaticRowStatus OBJECT-TYPE
  SYNTAX RowStatus
  ACCESS read-write
  STATUS mandatory
  DESCRIPTION
    "RowStatus of DHCP_STATIC_INT"
  ::= { mGuardDHCPIntStaticEntry 4 }

-- DHCP_STATIC_INT.COMMENT
mGuardDHCPIntStaticComment OBJECT-TYPE
  SYNTAX DisplayString
  ACCESS read-write
  STATUS mandatory
  DESCRIPTION
    "Variable name: DHCP_STATIC_INT.COMMENT
    WebUi Label: Comment
    Comment"
  ::= { mGuardDHCPIntStaticEntry 5 }

-- DHCP_STATIC_INT.IP
mGuardDHCPIntStaticIP OBJECT-TYPE
  SYNTAX IpAddress
  ACCESS read-write
  STATUS mandatory
  DESCRIPTION
    "Variable name: DHCP_STATIC_INT.IP
    WebUi Label: Client IP address
    The allocated IP address"
  ::= { mGuardDHCPIntStaticEntry 3 }

-- DHCP_STATIC_INT.MAC
mGuardDHCPIntStaticMAC OBJECT-TYPE
  SYNTAX MacAddress
  ACCESS read-write
  STATUS mandatory
  DESCRIPTION
    "Variable name: DHCP_STATIC_INT.MAC
    WebUi Label: Client MAC address
    The client's MAC address"
  ::= { mGuardDHCPIntStaticEntry 2 }


-- DMZ_ALIASES table
mGuardRouterDmzAliasesTable OBJECT-TYPE
  SYNTAX SEQUENCE OF MGuardRouterDmzAliasesEntry
  ACCESS not-accessible
  STATUS mandatory
  DESCRIPTION
    "A table of DMZ_ALIASES"
  ::= { mGuardRouterDmz 1 }

-- DMZ_ALIASES table entry
mGuardRouterDmzAliasesEntry OBJECT-TYPE
  SYNTAX MGuardRouterDmzAliasesEntry
  ACCESS not-accessible
  STATUS mandatory
  DESCRIPTION
    "An entry of DMZ_ALIASES"
  INDEX { mGuardDmzAliasIndex }
  ::= { mGuardRouterDmzAliasesTable 1 }

MGuardRouterDmzAliasesEntry ::= SEQUENCE {
  mGuardDmzAliasIndex                      INTEGER,
  mGuardDmzAliasIpAddress                  IpAddress,
  mGuardDmzAliasNetmask                    IpAddress,
  mGuardDmzAliasRowStatus                  RowStatus,
  mGuardDmzAliasOSPFAreaValue              INTEGER,
  mGuardDmzAliasOSPFAreaRef                OBJECT IDENTIFIER
}

-- DMZ_ALIASES table index
mGuardDmzAliasIndex OBJECT-TYPE
  SYNTAX INTEGER (1..2147483647)
  ACCESS not-accessible
  STATUS mandatory
  DESCRIPTION
    "Index to DMZ_ALIASES"
  ::= { mGuardRouterDmzAliasesEntry 1 }

-- DMZ_ALIASES row status
mGuardDmzAliasRowStatus OBJECT-TYPE
  SYNTAX RowStatus
  ACCESS read-write
  STATUS mandatory
  DESCRIPTION
    "RowStatus of DMZ_ALIASES"
  ::= { mGuardRouterDmzAliasesEntry 4 }

-- DMZ_ALIASES.DMZ_IP
mGuardDmzAliasIpAddress OBJECT-TYPE
  SYNTAX IpAddress
  ACCESS read-write
  STATUS mandatory
  DESCRIPTION
    "Variable name: DMZ_ALIASES.DMZ_IP
    WebUi Label: IP address
    IP address."
  ::= { mGuardRouterDmzAliasesEntry 2 }

-- DMZ_ALIASES.DMZ_NET
mGuardDmzAliasNetmask OBJECT-TYPE
  SYNTAX IpAddress
  ACCESS read-write
  STATUS mandatory
  DESCRIPTION
    "Variable name: DMZ_ALIASES.DMZ_NET
    WebUi Label: Netmask
    Netmask."
  ::= { mGuardRouterDmzAliasesEntry 3 }

-- DMZ_ALIASES.OSPF_AREA_REF
mGuardDmzAliasOSPFAreaValue OBJECT-TYPE
  SYNTAX INTEGER {
    none(1)
  }
  ACCESS read-write
  STATUS mandatory
  DESCRIPTION
    "Variable name: DMZ_ALIASES.OSPF_AREA_REF
    WebUi Label: OSPF area
    This object is effective if and only if the
    'mGuardDmzAliasOSPFAreaRef' object contains the OID of this object.
    When this object is read, it always returns the value 'none'. When the
    value 'none' is written to this object, no OSPF Area is used."
  ::= { mGuardRouterDmzAliasesEntry 7 }

-- DMZ_ALIASES.OSPF_AREA_REF reference
mGuardDmzAliasOSPFAreaRef OBJECT-TYPE
  SYNTAX OBJECT IDENTIFIER
  ACCESS read-write
  STATUS mandatory
  DESCRIPTION
    "Variable name: DMZ_ALIASES.OSPF_AREA_REF
    WebUi Label: OSPF area
    When this object contains the OID of an 'mGuardOSPFAreaIndex' object,
    the corresponding OSPF Area is attached to this alias. To select an
    OSPF Area in this manner, write the OID of the corresponding
    'mGuardOSPFAreaIndex' object to this object. To disable this feature,
    set the 'mGuardDmzAliasOSPFAreaValue' object."
  ::= { mGuardRouterDmzAliasesEntry 8 }


-- DMZ_ROUTES table
mGuardDmzRoutesTable OBJECT-TYPE
  SYNTAX SEQUENCE OF MGuardDmzRoutesEntry
  ACCESS not-accessible
  STATUS mandatory
  DESCRIPTION
    "A table of DMZ_ROUTES"
  ::= { mGuardRouterDmz 2 }

-- DMZ_ROUTES table entry
mGuardDmzRoutesEntry OBJECT-TYPE
  SYNTAX MGuardDmzRoutesEntry
  ACCESS not-accessible
  STATUS mandatory
  DESCRIPTION
    "An entry of DMZ_ROUTES"
  INDEX { mGuardDmzRouteIndex }
  ::= { mGuardDmzRoutesTable 1 }

MGuardDmzRoutesEntry ::= SEQUENCE {
  mGuardDmzRouteIndex                      INTEGER,
  mGuardDmzRouteNetwork                    DisplayString,
  mGuardDmzRouteGateway                    IpAddress,
  mGuardDmzRouteRowStatus                  RowStatus
}

-- DMZ_ROUTES table index
mGuardDmzRouteIndex OBJECT-TYPE
  SYNTAX INTEGER (1..2147483647)
  ACCESS not-accessible
  STATUS mandatory
  DESCRIPTION
    "Index to DMZ_ROUTES"
  ::= { mGuardDmzRoutesEntry 1 }

-- DMZ_ROUTES row status
mGuardDmzRouteRowStatus OBJECT-TYPE
  SYNTAX RowStatus
  ACCESS read-write
  STATUS mandatory
  DESCRIPTION
    "RowStatus of DMZ_ROUTES"
  ::= { mGuardDmzRoutesEntry 4 }

-- DMZ_ROUTES.GATEWAY
mGuardDmzRouteGateway OBJECT-TYPE
  SYNTAX IpAddress
  ACCESS read-write
  STATUS mandatory
  DESCRIPTION
    "Variable name: DMZ_ROUTES.GATEWAY
    WebUi Label: Gateway
    Routing gateway."
  ::= { mGuardDmzRoutesEntry 3 }

-- DMZ_ROUTES.NETWORK
mGuardDmzRouteNetwork OBJECT-TYPE
  SYNTAX DisplayString
  ACCESS read-write
  STATUS mandatory
  DESCRIPTION
    "Variable name: DMZ_ROUTES.NETWORK
    WebUi Label: Network
    Routed network."
  ::= { mGuardDmzRoutesEntry 2 }

-- DNSCACHE_ENABLED
mGuardDNSCacheEnabled OBJECT-TYPE
  SYNTAX INTEGER {
    yes(1),
    no(2)
  }
  ACCESS read-write
  STATUS mandatory
  DESCRIPTION
    "Variable name: DNSCACHE_ENABLED
    WebUi Label: --
    Enable or disable built-in DNS cache feature"
  ::= { mGuardDNS 4 }

-- DNSCACHE_MODE
mGuardDNSServerType OBJECT-TYPE
  SYNTAX INTEGER {
    root(1),
    provider(2),
    user(3)
  }
  ACCESS read-write
  STATUS mandatory
  DESCRIPTION
    "Variable name: DNSCACHE_MODE
    WebUi Label: Servers to query
    Type of DNS Servers to query: root: DNS root servers provider:
    Provider defined DNS Servers (via DHCP, PPPOE) user: User defined DNS
    Servers"
  ::= { mGuardDNS 2 }

-- DNSCACHE_SEARCHPATH
mGuardDNSSearchPath OBJECT-TYPE
  SYNTAX DisplayString
  ACCESS read-write
  STATUS mandatory
  DESCRIPTION
    "Variable name: DNSCACHE_SEARCHPATH
    WebUi Label: Domain search path
    Domain search path."
  ::= { mGuardDNS 1 }


-- DNSCACHE_USER_DEFINED table
mGuardDNSUserDefinedServerTable OBJECT-TYPE
  SYNTAX SEQUENCE OF MGuardDNSUserDefinedServerEntry
  ACCESS not-accessible
  STATUS mandatory
  DESCRIPTION
    "A table of DNSCACHE_USER_DEFINED"
  ::= { mGuardDNS 3 }

-- DNSCACHE_USER_DEFINED table entry
mGuardDNSUserDefinedServerEntry OBJECT-TYPE
  SYNTAX MGuardDNSUserDefinedServerEntry
  ACCESS not-accessible
  STATUS mandatory
  DESCRIPTION
    "An entry of DNSCACHE_USER_DEFINED"
  INDEX { mGuarddnsServerIndex }
  ::= { mGuardDNSUserDefinedServerTable 1 }

MGuardDNSUserDefinedServerEntry ::= SEQUENCE {
  mGuarddnsServerIndex                     INTEGER,
  mGuarddnsServerIP                        IpAddress,
  mGuarddnsServerRowStatus                 RowStatus
}

-- DNSCACHE_USER_DEFINED table index
mGuarddnsServerIndex OBJECT-TYPE
  SYNTAX INTEGER (1..2147483647)
  ACCESS not-accessible
  STATUS mandatory
  DESCRIPTION
    "Index to DNSCACHE_USER_DEFINED"
  ::= { mGuardDNSUserDefinedServerEntry 1 }

-- DNSCACHE_USER_DEFINED row status
mGuarddnsServerRowStatus OBJECT-TYPE
  SYNTAX RowStatus
  ACCESS read-write
  STATUS mandatory
  DESCRIPTION
    "RowStatus of DNSCACHE_USER_DEFINED"
  ::= { mGuardDNSUserDefinedServerEntry 3 }

-- DNSCACHE_USER_DEFINED.IP
mGuarddnsServerIP OBJECT-TYPE
  SYNTAX IpAddress
  ACCESS read-write
  STATUS mandatory
  DESCRIPTION
    "Variable name: DNSCACHE_USER_DEFINED.IP
    WebUi Label: IP
    DNS Server IP address."
  ::= { mGuardDNSUserDefinedServerEntry 2 }


-- DNS_ZONE table
mGuardDNSZoneTable OBJECT-TYPE
  SYNTAX SEQUENCE OF MGuardDNSZoneEntry
  ACCESS not-accessible
  STATUS mandatory
  DESCRIPTION
    "A table of DNS_ZONE"
  ::= { mGuardDNSZones 1 }

-- DNS_ZONE table entry
mGuardDNSZoneEntry OBJECT-TYPE
  SYNTAX MGuardDNSZoneEntry
  ACCESS not-accessible
  STATUS mandatory
  DESCRIPTION
    "An entry of DNS_ZONE"
  INDEX { mGuardDNSZoneIndex }
  ::= { mGuardDNSZoneTable 1 }

MGuardDNSZoneEntry ::= SEQUENCE {
  mGuardDNSZoneIndex                       INTEGER,
  mGuardDNSZoneEnabled                     INTEGER,
  mGuardDNSZoneDomainName                  DisplayString,
  mGuardDNSZoneRRPTREnabled                INTEGER,
  mGuardDNSZoneRowStatus                   RowStatus
}

-- DNS_ZONE table index
mGuardDNSZoneIndex OBJECT-TYPE
  SYNTAX INTEGER (1..2147483647)
  ACCESS not-accessible
  STATUS mandatory
  DESCRIPTION
    "Index to DNS_ZONE"
  ::= { mGuardDNSZoneEntry 1 }

-- DNS_ZONE row status
mGuardDNSZoneRowStatus OBJECT-TYPE
  SYNTAX RowStatus
  ACCESS read-write
  STATUS mandatory
  DESCRIPTION
    "RowStatus of DNS_ZONE"
  ::= { mGuardDNSZoneEntry 20 }

-- DNS_ZONE.ZONE_ENABLED
mGuardDNSZoneEnabled OBJECT-TYPE
  SYNTAX INTEGER {
    yes(1),
    no(2)
  }
  ACCESS read-write
  STATUS mandatory
  DESCRIPTION
    "Variable name: DNS_ZONE.ZONE_ENABLED
    WebUi Label: Enabled
    Set to 'yes' to enable this zone."
  ::= { mGuardDNSZoneEntry 2 }

-- DNS_ZONE.AUTO_RR_PTR_ENABLED
mGuardDNSZoneRRPTREnabled OBJECT-TYPE
  SYNTAX INTEGER {
    yes(1),
    no(2)
  }
  ACCESS read-write
  STATUS mandatory
  DESCRIPTION
    "Variable name: DNS_ZONE.AUTO_RR_PTR_ENABLED
    WebUi Label: Resolve IP addresses also
    Set to 'yes' to enable PTR resource records for this zone."
  ::= { mGuardDNSZoneEntry 4 }


-- DNS_ZONE.RR_A table
mGuardDNSZoneARecordTable OBJECT-TYPE
  SYNTAX SEQUENCE OF MGuardDNSZoneARecordEntry
  ACCESS not-accessible
  STATUS mandatory
  DESCRIPTION
    "A table of DNS_ZONE.RR_A"
  ::= { mGuardDNSZones 2 }

-- DNS_ZONE.RR_A table entry
mGuardDNSZoneARecordEntry OBJECT-TYPE
  SYNTAX MGuardDNSZoneARecordEntry
  ACCESS not-accessible
  STATUS mandatory
  DESCRIPTION
    "An entry of DNS_ZONE.RR_A"
  INDEX { mGuardDNSZoneIndex, mGuardDNSZoneARecRecIndex }
  ::= { mGuardDNSZoneARecordTable 1 }

MGuardDNSZoneARecordEntry ::= SEQUENCE {
  mGuardDNSZoneARecRecIndex                INTEGER,
  mGuardDNSZoneARecHostName                DisplayString,
  mGuardDNSZoneARecTTL                     INTEGER,
  mGuardDNSZoneARecIP                      IpAddress,
  mGuardDNSZoneARecRowStatus               RowStatus
}

-- DNS_ZONE.RR_A table index
mGuardDNSZoneARecRecIndex OBJECT-TYPE
  SYNTAX INTEGER (1..2147483647)
  ACCESS not-accessible
  STATUS mandatory
  DESCRIPTION
    "Index to DNS_ZONE.RR_A"
  ::= { mGuardDNSZoneARecordEntry 2 }

-- DNS_ZONE.RR_A row status
mGuardDNSZoneARecRowStatus OBJECT-TYPE
  SYNTAX RowStatus
  ACCESS read-write
  STATUS mandatory
  DESCRIPTION
    "RowStatus of DNS_ZONE.RR_A"
  ::= { mGuardDNSZoneARecordEntry 20 }

-- DNS_ZONE.RR_A.IP
mGuardDNSZoneARecIP OBJECT-TYPE
  SYNTAX IpAddress
  ACCESS read-write
  STATUS mandatory
  DESCRIPTION
    "Variable name: DNS_ZONE.RR_A.IP
    WebUi Label: IP
    The records's IP address"
  ::= { mGuardDNSZoneARecordEntry 5 }

-- DNS_ZONE.RR_A.TTL
mGuardDNSZoneARecTTL OBJECT-TYPE
  SYNTAX INTEGER(0..2147483647)
  ACCESS read-write
  STATUS mandatory
  DESCRIPTION
    "Variable name: DNS_ZONE.RR_A.TTL
    WebUi Label: TTL (hh:mm:ss)
    The record's TTL value."
  ::= { mGuardDNSZoneARecordEntry 4 }

-- DNS_ZONE.RR_A.LABEL
mGuardDNSZoneARecHostName OBJECT-TYPE
  SYNTAX DisplayString
  ACCESS read-write
  STATUS mandatory
  DESCRIPTION
    "Variable name: DNS_ZONE.RR_A.LABEL
    WebUi Label: Host
    The record's host name"
  ::= { mGuardDNSZoneARecordEntry 3 }

-- DNS_ZONE.DOMAIN_NAME
mGuardDNSZoneDomainName OBJECT-TYPE
  SYNTAX DisplayString
  ACCESS read-write
  STATUS mandatory
  DESCRIPTION
    "Variable name: DNS_ZONE.DOMAIN_NAME
    WebUi Label: Domain name
    The domain name to be used for this zone."
  ::= { mGuardDNSZoneEntry 3 }


-- DYNROUTING_ACCESSLIST table
mGuardDynRoutingACLTable OBJECT-TYPE
  SYNTAX SEQUENCE OF MGuardDynRoutingACLEntry
  ACCESS not-accessible
  STATUS mandatory
  DESCRIPTION
    "A table of DYNROUTING_ACCESSLIST"
  ::= { mGuardDynRouting 10 }

-- DYNROUTING_ACCESSLIST table entry
mGuardDynRoutingACLEntry OBJECT-TYPE
  SYNTAX MGuardDynRoutingACLEntry
  ACCESS not-accessible
  STATUS mandatory
  DESCRIPTION
    "An entry of DYNROUTING_ACCESSLIST"
  INDEX { mGuardDynRoutingACLIndex }
  ::= { mGuardDynRoutingACLTable 1 }

MGuardDynRoutingACLEntry ::= SEQUENCE {
  mGuardDynRoutingACLIndex                 INTEGER,
  mGuardDynRoutingACLRowStatus             RowStatus,
  mGuardDynRoutingACLName                  DisplayString
}

-- DYNROUTING_ACCESSLIST table index
mGuardDynRoutingACLIndex OBJECT-TYPE
  SYNTAX INTEGER (1..2147483647)
  ACCESS not-accessible
  STATUS mandatory
  DESCRIPTION
    "Index to DYNROUTING_ACCESSLIST"
  ::= { mGuardDynRoutingACLEntry 1 }

-- DYNROUTING_ACCESSLIST row status
mGuardDynRoutingACLRowStatus OBJECT-TYPE
  SYNTAX RowStatus
  ACCESS read-write
  STATUS mandatory
  DESCRIPTION
    "RowStatus of DYNROUTING_ACCESSLIST"
  ::= { mGuardDynRoutingACLEntry 2 }


-- DYNROUTING_ACCESSLIST.ENTRY table
mGuardDynRoutingACLRowTable OBJECT-TYPE
  SYNTAX SEQUENCE OF MGuardDynRoutingACLRowEntry
  ACCESS not-accessible
  STATUS mandatory
  DESCRIPTION
    "A table of DYNROUTING_ACCESSLIST.ENTRY"
  ::= { mGuardDynRouting 11 }

-- DYNROUTING_ACCESSLIST.ENTRY table entry
mGuardDynRoutingACLRowEntry OBJECT-TYPE
  SYNTAX MGuardDynRoutingACLRowEntry
  ACCESS not-accessible
  STATUS mandatory
  DESCRIPTION
    "An entry of DYNROUTING_ACCESSLIST.ENTRY"
  INDEX { mGuardDynRoutingACLIndex, mGuardDynRoutingACLRowIndex }
  ::= { mGuardDynRoutingACLRowTable 1 }

MGuardDynRoutingACLRowEntry ::= SEQUENCE {
  mGuardDynRoutingACLRowIndex              INTEGER,
  mGuardDynRoutingACLRowRowStatus          RowStatus,
  mGuardDynRoutingACLRowPermit             INTEGER,
  mGuardDynRoutingACLRowNet                DisplayString
}

-- DYNROUTING_ACCESSLIST.ENTRY table index
mGuardDynRoutingACLRowIndex OBJECT-TYPE
  SYNTAX INTEGER (1..2147483647)
  ACCESS not-accessible
  STATUS mandatory
  DESCRIPTION
    "Index to DYNROUTING_ACCESSLIST.ENTRY"
  ::= { mGuardDynRoutingACLRowEntry 1 }

-- DYNROUTING_ACCESSLIST.ENTRY row status
mGuardDynRoutingACLRowRowStatus OBJECT-TYPE
  SYNTAX RowStatus
  ACCESS read-write
  STATUS mandatory
  DESCRIPTION
    "RowStatus of DYNROUTING_ACCESSLIST.ENTRY"
  ::= { mGuardDynRoutingACLRowEntry 2 }

-- DYNROUTING_ACCESSLIST.ENTRY.NET
mGuardDynRoutingACLRowNet OBJECT-TYPE
  SYNTAX DisplayString
  ACCESS read-write
  STATUS mandatory
  DESCRIPTION
    "Variable name: DYNROUTING_ACCESSLIST.ENTRY.NET
    WebUi Label: Network
    Network value of row of an access list for dynamic routing."
  ::= { mGuardDynRoutingACLRowEntry 4 }

-- DYNROUTING_ACCESSLIST.ENTRY.PERMIT
mGuardDynRoutingACLRowPermit OBJECT-TYPE
  SYNTAX INTEGER {
    permit(1),
    deny(2)
  }
  ACCESS read-write
  STATUS mandatory
  DESCRIPTION
    "Variable name: DYNROUTING_ACCESSLIST.ENTRY.PERMIT
    WebUi Label: Permit/Deny
    Permit/Deny value of row of an access list for dynamic routing."
  ::= { mGuardDynRoutingACLRowEntry 3 }

-- DYNROUTING_ACCESSLIST.NAME
mGuardDynRoutingACLName OBJECT-TYPE
  SYNTAX DisplayString
  ACCESS read-write
  STATUS mandatory
  DESCRIPTION
    "Variable name: DYNROUTING_ACCESSLIST.NAME
    WebUi Label: Name
    Name of the access list, used for referencing in GUI."
  ::= { mGuardDynRoutingACLEntry 3 }

-- ECS_AUTOSAVE_ENABLE
mGuardProfileECSAutosaveEnable OBJECT-TYPE
  SYNTAX INTEGER {
    yes(1),
    no(2)
  }
  ACCESS read-write
  STATUS mandatory
  DESCRIPTION
    "Variable name: ECS_AUTOSAVE_ENABLE
    WebUi Label: Automatically save configuration changes to the ECS
    Will the configuration be automatically be saved to the external
    configuration storage (if present) upon every configuration change:
    yes / no."
  ::= { mGuardProfileECS 1 }

-- ECS_ENCRYPTION
mGuardProfileECSEncryption OBJECT-TYPE
  SYNTAX INTEGER {
    yes(1),
    no(2)
  }
  ACCESS read-write
  STATUS mandatory
  DESCRIPTION
    "Variable name: ECS_ENCRYPTION
    WebUi Label: Encrypt the data on the ECS
    Encrypt the configuration on the external configuration storage"
  ::= { mGuardProfileECS 2 }

-- ECS_LOAD_ON_BOOT
mGuardProfileECSLoadOnBoot OBJECT-TYPE
  SYNTAX INTEGER {
    yes(1),
    no(2)
  }
  ACCESS read-write
  STATUS mandatory
  DESCRIPTION
    "Variable name: ECS_LOAD_ON_BOOT
    WebUi Label: Load configuration from the ECS during boot
    Whether to load the ECS configuration on boot"
  ::= { mGuardProfileECS 3 }

-- EDS_DEBUG
mGuardEdsDebug OBJECT-TYPE
  SYNTAX INTEGER {
    yes(1),
    no(2)
  }
  ACCESS read-write
  STATUS mandatory
  DESCRIPTION
    "Variable name: EDS_DEBUG
    WebUi Label: Verbose EDS logging
    Enable logging of EDS state changes (yes, no)"
  ::= { mGuardLogging 5 }

-- EMAIL_FROM
mGuardEMailAddressFrom OBJECT-TYPE
  SYNTAX DisplayString
  ACCESS read-write
  STATUS mandatory
  DESCRIPTION
    "Variable name: EMAIL_FROM
    WebUi Label: Sender address of e-mail notifications
    E-Mail address that is used as the sender address for outgoing
    E-mails."
  ::= { mGuardEmailSetting 1 }


-- EMAIL_NOTIFICATION table
mGuardEmailNotificationTable OBJECT-TYPE
  SYNTAX SEQUENCE OF MGuardEmailNotificationEntry
  ACCESS not-accessible
  STATUS mandatory
  DESCRIPTION
    "A table of EMAIL_NOTIFICATION"
  ::= { mGuardEmailSetting 8 }

-- EMAIL_NOTIFICATION table entry
mGuardEmailNotificationEntry OBJECT-TYPE
  SYNTAX MGuardEmailNotificationEntry
  ACCESS not-accessible
  STATUS mandatory
  DESCRIPTION
    "An entry of EMAIL_NOTIFICATION"
  INDEX { mGuardEmailNotificationIndex }
  ::= { mGuardEmailNotificationTable 1 }

MGuardEmailNotificationEntry ::= SEQUENCE {
  mGuardEmailNotificationIndex             INTEGER,
  mGuardEmailNotificationTo                DisplayString,
  mGuardEmailNotificationSubject           DisplayString,
  mGuardEmailNotificationMessage           DisplayString,
  mGuardEmailNotificationEvent             DisplayString,
  mGuardEmailNotificationSelectorValue     INTEGER,
  mGuardEmailNotificationSelectorRef       OBJECT IDENTIFIER,
  mGuardEmailNotificationRowStatus         RowStatus,
  mGuardEmailNotificationFWRuleValue       INTEGER,
  mGuardEmailNotificationFWRuleRef         OBJECT IDENTIFIER,
  mGuardEmailNotificationSelectorOpenVPNValue INTEGER,
  mGuardEmailNotificationSelectorOpenVPNRef OBJECT IDENTIFIER
}

-- EMAIL_NOTIFICATION table index
mGuardEmailNotificationIndex OBJECT-TYPE
  SYNTAX INTEGER (1..2147483647)
  ACCESS not-accessible
  STATUS mandatory
  DESCRIPTION
    "Index to EMAIL_NOTIFICATION"
  ::= { mGuardEmailNotificationEntry 1 }

-- EMAIL_NOTIFICATION row status
mGuardEmailNotificationRowStatus OBJECT-TYPE
  SYNTAX RowStatus
  ACCESS read-write
  STATUS mandatory
  DESCRIPTION
    "RowStatus of EMAIL_NOTIFICATION"
  ::= { mGuardEmailNotificationEntry 8 }

-- EMAIL_NOTIFICATION.SELECTOR_OPENVPN
mGuardEmailNotificationSelectorOpenVPNValue OBJECT-TYPE
  SYNTAX INTEGER {
    none(1)
  }
  ACCESS read-write
  STATUS mandatory
  DESCRIPTION
    "Variable name: EMAIL_NOTIFICATION.SELECTOR_OPENVPN
    WebUi Label: OpenVPN selector
    "
  ::= { mGuardEmailNotificationEntry 11 }

-- EMAIL_NOTIFICATION.SELECTOR_OPENVPN reference
mGuardEmailNotificationSelectorOpenVPNRef OBJECT-TYPE
  SYNTAX OBJECT IDENTIFIER
  ACCESS read-write
  STATUS mandatory
  DESCRIPTION
    "Variable name: EMAIL_NOTIFICATION.SELECTOR_OPENVPN
    WebUi Label: OpenVPN selector
    "
  ::= { mGuardEmailNotificationEntry 12 }

-- EMAIL_NOTIFICATION.SELECTOR
mGuardEmailNotificationSelectorValue OBJECT-TYPE
  SYNTAX INTEGER {
    none(1)
  }
  ACCESS read-write
  STATUS mandatory
  DESCRIPTION
    "Variable name: EMAIL_NOTIFICATION.SELECTOR
    WebUi Label: IPsec selector
    Configures the VPN connection to watch"
  ::= { mGuardEmailNotificationEntry 6 }

-- EMAIL_NOTIFICATION.SELECTOR reference
mGuardEmailNotificationSelectorRef OBJECT-TYPE
  SYNTAX OBJECT IDENTIFIER
  ACCESS read-write
  STATUS mandatory
  DESCRIPTION
    "Variable name: EMAIL_NOTIFICATION.SELECTOR
    WebUi Label: IPsec selector
    When this object contains the OID of a 'mGuardVPNconIndex' or
    'mGuardOpenVPNConnectionIndex' object, the corresponding connection is
    used for this notification. To disable this feature, set the OID of
    the 'mGuardEmailNotificationSelectorValue' object."
  ::= { mGuardEmailNotificationEntry 7 }

-- EMAIL_NOTIFICATION.TO
mGuardEmailNotificationTo OBJECT-TYPE
  SYNTAX DisplayString
  ACCESS read-write
  STATUS mandatory
  DESCRIPTION
    "Variable name: EMAIL_NOTIFICATION.TO
    WebUi Label: E-Mail recipient
    Sets the receiver email address"
  ::= { mGuardEmailNotificationEntry 2 }

-- EMAIL_NOTIFICATION.SELECTOR_FW_RULESET
mGuardEmailNotificationFWRuleValue OBJECT-TYPE
  SYNTAX INTEGER {
    none(1)
  }
  ACCESS read-write
  STATUS mandatory
  DESCRIPTION
    "Variable name: EMAIL_NOTIFICATION.SELECTOR_FW_RULESET
    WebUi Label: Rule record selector
    When read, this object will always return the value 'none'. When the
    value 'none' is written to this object, any association of this
    notification with a firewall rule set will be deleted from the
    'mGuardEmailNotificationFWRuleRef' object."
  ::= { mGuardEmailNotificationEntry 9 }

-- EMAIL_NOTIFICATION.SELECTOR_FW_RULESET reference
mGuardEmailNotificationFWRuleRef OBJECT-TYPE
  SYNTAX OBJECT IDENTIFIER
  ACCESS read-write
  STATUS mandatory
  DESCRIPTION
    "Variable name: EMAIL_NOTIFICATION.SELECTOR_FW_RULESET
    WebUi Label: Rule record selector
    Set this object to an 'mGuardFWRuleIndex' object to associate this
    notification with a firewall rule set. Set the object
    'mGuardEmailNotificationFWRuleValue' to disable this association. For
    this feature to work, you also have to set the object
    'mGuardEmailNotificationEvent' appropriately."
  ::= { mGuardEmailNotificationEntry 10 }

-- EMAIL_NOTIFICATION.MESSAGE
mGuardEmailNotificationMessage OBJECT-TYPE
  SYNTAX DisplayString
  ACCESS read-write
  STATUS mandatory
  DESCRIPTION
    "Variable name: EMAIL_NOTIFICATION.MESSAGE
    WebUi Label: E-Mail message
    Sets the message to be send"
  ::= { mGuardEmailNotificationEntry 4 }

-- EMAIL_NOTIFICATION.EVENT
mGuardEmailNotificationEvent OBJECT-TYPE
  SYNTAX DisplayString
  ACCESS read-write
  STATUS mandatory
  DESCRIPTION
    "Variable name: EMAIL_NOTIFICATION.EVENT
    WebUi Label: Event
    Configures the event which will initiate sending this email"
  ::= { mGuardEmailNotificationEntry 5 }

-- EMAIL_NOTIFICATION.SUBJECT
mGuardEmailNotificationSubject OBJECT-TYPE
  SYNTAX DisplayString
  ACCESS read-write
  STATUS mandatory
  DESCRIPTION
    "Variable name: EMAIL_NOTIFICATION.SUBJECT
    WebUi Label: E-Mail subject
    Sets the email subject"
  ::= { mGuardEmailNotificationEntry 3 }

-- EMAIL_RELAY_HOST
mGuardEMailServer OBJECT-TYPE
  SYNTAX DisplayString
  ACCESS read-write
  STATUS mandatory
  DESCRIPTION
    "Variable name: EMAIL_RELAY_HOST
    WebUi Label: Address of the e-mail server
    IP address or hostname of E-Mail-server used to send E-Mails."
  ::= { mGuardEmailSetting 2 }

-- EMAIL_RELAY_LOGIN
mGuardEMailAuthUser OBJECT-TYPE
  SYNTAX DisplayString
  ACCESS read-write
  STATUS mandatory
  DESCRIPTION
    "Variable name: EMAIL_RELAY_LOGIN
    WebUi Label: SMTP user name
    Username for E-mail server authentication"
  ::= { mGuardEmailSetting 6 }

-- EMAIL_RELAY_PASSWORD
mGuardEMailAuthPassword OBJECT-TYPE
  SYNTAX DisplayString
  ACCESS read-write
  STATUS mandatory
  DESCRIPTION
    "Variable name: EMAIL_RELAY_PASSWORD
    WebUi Label: SMTP password
    Password for E-mail server authentication"
  ::= { mGuardEmailSetting 7 }

-- EMAIL_RELAY_PORT
mGuardEMailPort OBJECT-TYPE
  SYNTAX INTEGER(1..65535)
  ACCESS read-write
  STATUS mandatory
  DESCRIPTION
    "Variable name: EMAIL_RELAY_PORT
    WebUi Label: Port number of the e-mail server
    Port of E-Mail-server used to send E-Mails, usually 25."
  ::= { mGuardEmailSetting 3 }

-- EMAIL_RELAY_TLS
mGuardEMailTLS OBJECT-TYPE
  SYNTAX INTEGER {
    none(1),
    tls(2),
    starttls(3)
  }
  ACCESS read-write
  STATUS mandatory
  DESCRIPTION
    "Variable name: EMAIL_RELAY_TLS
    WebUi Label: Encryption mode for the e-mail server
    E-mail transport layer security"
  ::= { mGuardEmailSetting 4 }

-- EXT2_DNS_MODE
mGuardNetworkExt2DNSServerType OBJECT-TYPE
  SYNTAX INTEGER {
    root(1),
    provider(2),
    user(3),
    none(1000)
  }
  ACCESS read-write
  STATUS mandatory
  DESCRIPTION
    "Variable name: EXT2_DNS_MODE
    WebUi Label: DNS mode
    DNS mode for alternative path"
  ::= { mGuardNetworkExt2 5 }


-- EXT2_DNS_USER_DEFINED table
mGuardDNSExt2UserDefinedServerTable OBJECT-TYPE
  SYNTAX SEQUENCE OF MGuardDNSExt2UserDefinedServerEntry
  ACCESS not-accessible
  STATUS mandatory
  DESCRIPTION
    "A table of EXT2_DNS_USER_DEFINED"
  ::= { mGuardDNS 6 }

-- EXT2_DNS_USER_DEFINED table entry
mGuardDNSExt2UserDefinedServerEntry OBJECT-TYPE
  SYNTAX MGuardDNSExt2UserDefinedServerEntry
  ACCESS not-accessible
  STATUS mandatory
  DESCRIPTION
    "An entry of EXT2_DNS_USER_DEFINED"
  INDEX { mGuarddnsExt2ServerIndex }
  ::= { mGuardDNSExt2UserDefinedServerTable 1 }

MGuardDNSExt2UserDefinedServerEntry ::= SEQUENCE {
  mGuarddnsExt2ServerIndex                 INTEGER,
  mGuarddnsExt2ServerIP                    IpAddress,
  mGuarddnsExt2ServerRowStatus             RowStatus
}

-- EXT2_DNS_USER_DEFINED table index
mGuarddnsExt2ServerIndex OBJECT-TYPE
  SYNTAX INTEGER (1..2147483647)
  ACCESS not-accessible
  STATUS mandatory
  DESCRIPTION
    "Index to EXT2_DNS_USER_DEFINED"
  ::= { mGuardDNSExt2UserDefinedServerEntry 1 }

-- EXT2_DNS_USER_DEFINED row status
mGuarddnsExt2ServerRowStatus OBJECT-TYPE
  SYNTAX RowStatus
  ACCESS read-write
  STATUS mandatory
  DESCRIPTION
    "RowStatus of EXT2_DNS_USER_DEFINED"
  ::= { mGuardDNSExt2UserDefinedServerEntry 3 }

-- EXT2_DNS_USER_DEFINED.IP
mGuarddnsExt2ServerIP OBJECT-TYPE
  SYNTAX IpAddress
  ACCESS read-write
  STATUS mandatory
  DESCRIPTION
    "Variable name: EXT2_DNS_USER_DEFINED.IP
    WebUi Label: DNS Server
    DNS Server IP address."
  ::= { mGuardDNSExt2UserDefinedServerEntry 2 }

-- EXT2_OPERATIONMODE
mGuardNetworkExt2OpMode OBJECT-TYPE
  SYNTAX INTEGER {
    permanent(1),
    fallback(2)
  }
  ACCESS read-write
  STATUS mandatory
  DESCRIPTION
    "Variable name: EXT2_OPERATIONMODE
    WebUi Label: Operation mode
    Operation mode for alternative path: permanent or fallback"
  ::= { mGuardNetworkExt2 2 }


-- EXT2_PROBE table
mGuardNetworkExt2ProbeTable OBJECT-TYPE
  SYNTAX SEQUENCE OF MGuardNetworkExt2ProbeEntry
  ACCESS not-accessible
  STATUS mandatory
  DESCRIPTION
    "A table of EXT2_PROBE"
  ::= { mGuardNetworkExt2Probe 1 }

-- EXT2_PROBE table entry
mGuardNetworkExt2ProbeEntry OBJECT-TYPE
  SYNTAX MGuardNetworkExt2ProbeEntry
  ACCESS not-accessible
  STATUS mandatory
  DESCRIPTION
    "An entry of EXT2_PROBE"
  INDEX { mGuardNetworkExt2ProbeIndex }
  ::= { mGuardNetworkExt2ProbeTable 1 }

MGuardNetworkExt2ProbeEntry ::= SEQUENCE {
  mGuardNetworkExt2ProbeIndex              INTEGER,
  mGuardNetworkExt2ProbeType               INTEGER,
  mGuardNetworkExt2ProbeDest               DisplayString,
  mGuardNetworkExt2ProbeComment            DisplayString,
  mGuardNetworkExt2ProbeRowStatus          RowStatus
}

-- EXT2_PROBE table index
mGuardNetworkExt2ProbeIndex OBJECT-TYPE
  SYNTAX INTEGER (1..2147483647)
  ACCESS not-accessible
  STATUS mandatory
  DESCRIPTION
    "Index to EXT2_PROBE"
  ::= { mGuardNetworkExt2ProbeEntry 1 }

-- EXT2_PROBE row status
mGuardNetworkExt2ProbeRowStatus OBJECT-TYPE
  SYNTAX RowStatus
  ACCESS read-write
  STATUS mandatory
  DESCRIPTION
    "RowStatus of EXT2_PROBE"
  ::= { mGuardNetworkExt2ProbeEntry 5 }

-- EXT2_PROBE.COMMENT
mGuardNetworkExt2ProbeComment OBJECT-TYPE
  SYNTAX DisplayString
  ACCESS read-write
  STATUS mandatory
  DESCRIPTION
    "Variable name: EXT2_PROBE.COMMENT
    WebUi Label: Comment
    Commentary or name for this probe."
  ::= { mGuardNetworkExt2ProbeEntry 4 }

-- EXT2_PROBE.DESTINATION
mGuardNetworkExt2ProbeDest OBJECT-TYPE
  SYNTAX DisplayString
  ACCESS read-write
  STATUS mandatory
  DESCRIPTION
    "Variable name: EXT2_PROBE.DESTINATION
    WebUi Label: Destination
    The probe destination to monitor"
  ::= { mGuardNetworkExt2ProbeEntry 3 }

-- EXT2_PROBE.TYPE
mGuardNetworkExt2ProbeType OBJECT-TYPE
  SYNTAX INTEGER {
    icmpping(1),
    dnsping(2),
    ikeping(3)
  }
  ACCESS read-write
  STATUS mandatory
  DESCRIPTION
    "Variable name: EXT2_PROBE.TYPE
    WebUi Label: Type
    The operation type used to probe."
  ::= { mGuardNetworkExt2ProbeEntry 2 }

-- EXT2_PROBE_FAILCOUNT
mGuardNetworkExt2ProbeMaxCount OBJECT-TYPE
  SYNTAX INTEGER(1..5)
  ACCESS read-write
  STATUS mandatory
  DESCRIPTION
    "Variable name: EXT2_PROBE_FAILCOUNT
    WebUi Label: Number of times all probes need to fail during subsequent runs before
     the secondary external interface is activated
    Maximum number of probe attempts before flagging failure."
  ::= { mGuardNetworkExt2Probe 2 }

-- EXT2_PROBE_INTERVAL_SECONDS
mGuardNetworkExt2ProbeInterval OBJECT-TYPE
  SYNTAX INTEGER(10..120)
  ACCESS read-write
  STATUS mandatory
  DESCRIPTION
    "Variable name: EXT2_PROBE_INTERVAL_SECONDS
    WebUi Label: Probe interval
    Interval between probe runs."
  ::= { mGuardNetworkExt2Probe 3 }


-- EXT2_ROUTE table
mGuardNetworkExt2RoutesTable OBJECT-TYPE
  SYNTAX SEQUENCE OF MGuardNetworkExt2RoutesEntry
  ACCESS not-accessible
  STATUS mandatory
  DESCRIPTION
    "A table of EXT2_ROUTE"
  ::= { mGuardNetworkExt2 4 }

-- EXT2_ROUTE table entry
mGuardNetworkExt2RoutesEntry OBJECT-TYPE
  SYNTAX MGuardNetworkExt2RoutesEntry
  ACCESS not-accessible
  STATUS mandatory
  DESCRIPTION
    "An entry of EXT2_ROUTE"
  INDEX { mGuardNetworkExt2RoutesIndex }
  ::= { mGuardNetworkExt2RoutesTable 1 }

MGuardNetworkExt2RoutesEntry ::= SEQUENCE {
  mGuardNetworkExt2RoutesIndex             INTEGER,
  mGuardNetworkExt2RoutesNetwork           DisplayString,
  mGuardNetworkExt2RoutesGateway           DisplayString,
  mGuardNetworkExt2RoutesRowStatus         RowStatus
}

-- EXT2_ROUTE table index
mGuardNetworkExt2RoutesIndex OBJECT-TYPE
  SYNTAX INTEGER (1..2147483647)
  ACCESS not-accessible
  STATUS mandatory
  DESCRIPTION
    "Index to EXT2_ROUTE"
  ::= { mGuardNetworkExt2RoutesEntry 1 }

-- EXT2_ROUTE row status
mGuardNetworkExt2RoutesRowStatus OBJECT-TYPE
  SYNTAX RowStatus
  ACCESS read-write
  STATUS mandatory
  DESCRIPTION
    "RowStatus of EXT2_ROUTE"
  ::= { mGuardNetworkExt2RoutesEntry 4 }

-- EXT2_ROUTE.GATEWAY
mGuardNetworkExt2RoutesGateway OBJECT-TYPE
  SYNTAX DisplayString
  ACCESS read-write
  STATUS mandatory
  DESCRIPTION
    "Variable name: EXT2_ROUTE.GATEWAY
    WebUi Label: Gateway
    The gateway IP address or '%gateway' for the provider defined gateway"
  ::= { mGuardNetworkExt2RoutesEntry 3 }

-- EXT2_ROUTE.NETWORK
mGuardNetworkExt2RoutesNetwork OBJECT-TYPE
  SYNTAX DisplayString
  ACCESS read-write
  STATUS mandatory
  DESCRIPTION
    "Variable name: EXT2_ROUTE.NETWORK
    WebUi Label: Network
    The routing destination in x.x.x.x/bits syntax"
  ::= { mGuardNetworkExt2RoutesEntry 2 }

-- EXT2_ROUTERMODE
mGuardNetworkExt2Mode OBJECT-TYPE
  SYNTAX INTEGER {
    modem(5),
    modemint(6),
    gsm(7),
    none(1000)
  }
  ACCESS read-write
  STATUS mandatory
  DESCRIPTION
    "Variable name: EXT2_ROUTERMODE
    WebUi Label: Network mode
    Network mode for alternative path: modem or modem internal"
  ::= { mGuardNetworkExt2 1 }

-- EXT2_USE_PROXY
mGuardNetworkExt2UseProxy OBJECT-TYPE
  SYNTAX INTEGER {
    yes(1),
    no(2)
  }
  ACCESS read-write
  STATUS mandatory
  DESCRIPTION
    "Variable name: EXT2_USE_PROXY
    WebUi Label: Secondary external interface uses proxy
    Use configured HTTP(S) proxy on secondary external interface?"
  ::= { mGuardNetworkExt2 6 }


-- EXTERN_ALIASES table
mGuardRouterExternAliasesTable OBJECT-TYPE
  SYNTAX SEQUENCE OF MGuardRouterExternAliasesEntry
  ACCESS not-accessible
  STATUS mandatory
  DESCRIPTION
    "A table of EXTERN_ALIASES"
  ::= { mGuardRouterExternStatic 5 }

-- EXTERN_ALIASES table entry
mGuardRouterExternAliasesEntry OBJECT-TYPE
  SYNTAX MGuardRouterExternAliasesEntry
  ACCESS not-accessible
  STATUS mandatory
  DESCRIPTION
    "An entry of EXTERN_ALIASES"
  INDEX { mGuardExternAliasIndex }
  ::= { mGuardRouterExternAliasesTable 1 }

MGuardRouterExternAliasesEntry ::= SEQUENCE {
  mGuardExternAliasIndex                   INTEGER,
  mGuardExternAliasIpAddress               IpAddress,
  mGuardExternAliasNetmask                 IpAddress,
  mGuardExternAliasRowStatus               RowStatus,
  mGuardExternAliasUseVLAN                 INTEGER,
  mGuardExternAliasVLANid                  INTEGER,
  mGuardExternAliasOSPFAreaValue           INTEGER,
  mGuardExternAliasOSPFAreaRef             OBJECT IDENTIFIER
}

-- EXTERN_ALIASES table index
mGuardExternAliasIndex OBJECT-TYPE
  SYNTAX INTEGER (1..2147483647)
  ACCESS not-accessible
  STATUS mandatory
  DESCRIPTION
    "Index to EXTERN_ALIASES"
  ::= { mGuardRouterExternAliasesEntry 1 }

-- EXTERN_ALIASES row status
mGuardExternAliasRowStatus OBJECT-TYPE
  SYNTAX RowStatus
  ACCESS read-write
  STATUS mandatory
  DESCRIPTION
    "RowStatus of EXTERN_ALIASES"
  ::= { mGuardRouterExternAliasesEntry 4 }

-- EXTERN_ALIASES.USE_VLAN
mGuardExternAliasUseVLAN OBJECT-TYPE
  SYNTAX INTEGER {
    yes(1),
    no(2)
  }
  ACCESS read-write
  STATUS mandatory
  DESCRIPTION
    "Variable name: EXTERN_ALIASES.USE_VLAN
    WebUi Label: Use VLAN
    Use VLAN tagging with this Alias interface."
  ::= { mGuardRouterExternAliasesEntry 5 }

-- EXTERN_ALIASES.EXTERN_IP
mGuardExternAliasIpAddress OBJECT-TYPE
  SYNTAX IpAddress
  ACCESS read-write
  STATUS mandatory
  DESCRIPTION
    "Variable name: EXTERN_ALIASES.EXTERN_IP
    WebUi Label: IP address
    IP address."
  ::= { mGuardRouterExternAliasesEntry 2 }

-- EXTERN_ALIASES.EXTERN_NET
mGuardExternAliasNetmask OBJECT-TYPE
  SYNTAX IpAddress
  ACCESS read-write
  STATUS mandatory
  DESCRIPTION
    "Variable name: EXTERN_ALIASES.EXTERN_NET
    WebUi Label: Netmask
    Netmask."
  ::= { mGuardRouterExternAliasesEntry 3 }

-- EXTERN_ALIASES.VLAN_ID
mGuardExternAliasVLANid OBJECT-TYPE
  SYNTAX INTEGER(1..4094)
  ACCESS read-write
  STATUS mandatory
  DESCRIPTION
    "Variable name: EXTERN_ALIASES.VLAN_ID
    WebUi Label: VLAN ID
    VLAN ID to be used with this Alias."
  ::= { mGuardRouterExternAliasesEntry 6 }

-- EXTERN_ALIASES.OSPF_AREA_REF
mGuardExternAliasOSPFAreaValue OBJECT-TYPE
  SYNTAX INTEGER {
    none(1)
  }
  ACCESS read-write
  STATUS mandatory
  DESCRIPTION
    "Variable name: EXTERN_ALIASES.OSPF_AREA_REF
    WebUi Label: OSPF area
    This object is effective if and only if the
    'mGuardExternAliasOSPFAreaRef' object contains the OID of this object.
    When this object is read, it always returns the value 'none'. When the
    value 'none' is written to this object, no OSPF Area is used."
  ::= { mGuardRouterExternAliasesEntry 7 }

-- EXTERN_ALIASES.OSPF_AREA_REF reference
mGuardExternAliasOSPFAreaRef OBJECT-TYPE
  SYNTAX OBJECT IDENTIFIER
  ACCESS read-write
  STATUS mandatory
  DESCRIPTION
    "Variable name: EXTERN_ALIASES.OSPF_AREA_REF
    WebUi Label: OSPF area
    When this object contains the OID of an 'mGuardOSPFAreaIndex' object,
    the corresponding OSPF Area is attached to this alias. To select an
    OSPF Area in this manner, write the OID of the corresponding
    'mGuardOSPFAreaIndex' object to this object. To disable this feature,
    set the 'mGuardExternAliasOSPFAreaValue' object."
  ::= { mGuardRouterExternAliasesEntry 8 }


-- EXTERN_ROUTES table
mGuardExternRoutesTable OBJECT-TYPE
  SYNTAX SEQUENCE OF MGuardExternRoutesEntry
  ACCESS not-accessible
  STATUS mandatory
  DESCRIPTION
    "A table of EXTERN_ROUTES"
  ::= { mGuardRouterExternStatic 6 }

-- EXTERN_ROUTES table entry
mGuardExternRoutesEntry OBJECT-TYPE
  SYNTAX MGuardExternRoutesEntry
  ACCESS not-accessible
  STATUS mandatory
  DESCRIPTION
    "An entry of EXTERN_ROUTES"
  INDEX { mGuardExternRouteIndex }
  ::= { mGuardExternRoutesTable 1 }

MGuardExternRoutesEntry ::= SEQUENCE {
  mGuardExternRouteIndex                   INTEGER,
  mGuardExternRouteNetwork                 DisplayString,
  mGuardExternRouteGateway                 IpAddress,
  mGuardExternRouteRowStatus               RowStatus
}

-- EXTERN_ROUTES table index
mGuardExternRouteIndex OBJECT-TYPE
  SYNTAX INTEGER (1..2147483647)
  ACCESS not-accessible
  STATUS mandatory
  DESCRIPTION
    "Index to EXTERN_ROUTES"
  ::= { mGuardExternRoutesEntry 1 }

-- EXTERN_ROUTES row status
mGuardExternRouteRowStatus OBJECT-TYPE
  SYNTAX RowStatus
  ACCESS read-write
  STATUS mandatory
  DESCRIPTION
    "RowStatus of EXTERN_ROUTES"
  ::= { mGuardExternRoutesEntry 4 }

-- EXTERN_ROUTES.GATEWAY
mGuardExternRouteGateway OBJECT-TYPE
  SYNTAX IpAddress
  ACCESS read-write
  STATUS mandatory
  DESCRIPTION
    "Variable name: EXTERN_ROUTES.GATEWAY
    WebUi Label: Gateway
    Routing gateway."
  ::= { mGuardExternRoutesEntry 3 }

-- EXTERN_ROUTES.NETWORK
mGuardExternRouteNetwork OBJECT-TYPE
  SYNTAX DisplayString
  ACCESS read-write
  STATUS mandatory
  DESCRIPTION
    "Variable name: EXTERN_ROUTES.NETWORK
    WebUi Label: Network
    Routed network."
  ::= { mGuardExternRoutesEntry 2 }


-- FW_1TO1_NAT table
mGuardFirewall11NATRuleTable OBJECT-TYPE
  SYNTAX SEQUENCE OF MGuardFirewall11NATRuleEntry
  ACCESS not-accessible
  STATUS mandatory
  DESCRIPTION
    "A table of FW_1TO1_NAT"
  ::= { mGuardFirewall11NAT 1 }

-- FW_1TO1_NAT table entry
mGuardFirewall11NATRuleEntry OBJECT-TYPE
  SYNTAX MGuardFirewall11NATRuleEntry
  ACCESS not-accessible
  STATUS mandatory
  DESCRIPTION
    "An entry of FW_1TO1_NAT"
  INDEX { mGuardFW11NATruleIndex }
  ::= { mGuardFirewall11NATRuleTable 1 }

MGuardFirewall11NATRuleEntry ::= SEQUENCE {
  mGuardFW11NATruleIndex                   INTEGER,
  mGuardFW11NATLocal                       IpAddress,
  mGuardFW11NATRemote                      IpAddress,
  mGuardFW11NATMask                        INTEGER,
  mGuardFW11NATComment                     DisplayString,
  mGuardFW11NATArpEnable                   INTEGER,
  mGuardFW11NATRowStatus                   RowStatus
}

-- FW_1TO1_NAT table index
mGuardFW11NATruleIndex OBJECT-TYPE
  SYNTAX INTEGER (1..2147483647)
  ACCESS not-accessible
  STATUS mandatory
  DESCRIPTION
    "Index to FW_1TO1_NAT"
  ::= { mGuardFirewall11NATRuleEntry 1 }

-- FW_1TO1_NAT row status
mGuardFW11NATRowStatus OBJECT-TYPE
  SYNTAX RowStatus
  ACCESS read-write
  STATUS mandatory
  DESCRIPTION
    "RowStatus of FW_1TO1_NAT"
  ::= { mGuardFirewall11NATRuleEntry 10 }

-- FW_1TO1_NAT.COMMENT
mGuardFW11NATComment OBJECT-TYPE
  SYNTAX DisplayString
  ACCESS read-write
  STATUS mandatory
  DESCRIPTION
    "Variable name: FW_1TO1_NAT.COMMENT
    WebUi Label: Comment
    Commentary or name for this rule."
  ::= { mGuardFirewall11NATRuleEntry 6 }

-- FW_1TO1_NAT.ENABLE_ARP
mGuardFW11NATArpEnable OBJECT-TYPE
  SYNTAX INTEGER {
    yes(1),
    no(2)
  }
  ACCESS read-write
  STATUS mandatory
  DESCRIPTION
    "Variable name: FW_1TO1_NAT.ENABLE_ARP
    WebUi Label: Enable ARP
    Whether ARP resolution shall be done for the network."
  ::= { mGuardFirewall11NATRuleEntry 7 }

-- FW_1TO1_NAT.REMOTE_NET
mGuardFW11NATRemote OBJECT-TYPE
  SYNTAX IpAddress
  ACCESS read-write
  STATUS mandatory
  DESCRIPTION
    "Variable name: FW_1TO1_NAT.REMOTE_NET
    WebUi Label: Virtual network
    Network for 1:1 NAT on remote interface."
  ::= { mGuardFirewall11NATRuleEntry 3 }

-- FW_1TO1_NAT.LOCAL_NET
mGuardFW11NATLocal OBJECT-TYPE
  SYNTAX IpAddress
  ACCESS read-write
  STATUS mandatory
  DESCRIPTION
    "Variable name: FW_1TO1_NAT.LOCAL_NET
    WebUi Label: Real network
    Network for 1:1 NAT on local interface."
  ::= { mGuardFirewall11NATRuleEntry 2 }

-- FW_1TO1_NAT.MASK
mGuardFW11NATMask OBJECT-TYPE
  SYNTAX INTEGER(1..32)
  ACCESS read-write
  STATUS mandatory
  DESCRIPTION
    "Variable name: FW_1TO1_NAT.MASK
    WebUi Label: Netmask
    Netmask for 1:1 NAT between 0 and 32."
  ::= { mGuardFirewall11NATRuleEntry 4 }

-- FW_CONNTRACK_FLUSH
mGuardFirewallConntrackFlush OBJECT-TYPE
  SYNTAX INTEGER {
    yes(1),
    no(2)
  }
  ACCESS read-write
  STATUS mandatory
  DESCRIPTION
    "Variable name: FW_CONNTRACK_FLUSH
    WebUi Label: Abort existing connections upon firewall reconfiguration
    Abort existing connections upon firewall reconfiguration"
  ::= { mGuardFirewallExtended 21 }


-- FW_GROUP_IP table
mGuardFirewallGroupIPv4Table OBJECT-TYPE
  SYNTAX SEQUENCE OF MGuardFirewallGroupIPv4Entry
  ACCESS not-accessible
  STATUS mandatory
  DESCRIPTION
    "A table of FW_GROUP_IP"
  ::= { mGuardFirewallGroupIPv4 1 }

-- FW_GROUP_IP table entry
mGuardFirewallGroupIPv4Entry OBJECT-TYPE
  SYNTAX MGuardFirewallGroupIPv4Entry
  ACCESS not-accessible
  STATUS mandatory
  DESCRIPTION
    "An entry of FW_GROUP_IP"
  INDEX { mGuardFirewallGroupIPv4Index }
  ::= { mGuardFirewallGroupIPv4Table 1 }

MGuardFirewallGroupIPv4Entry ::= SEQUENCE {
  mGuardFirewallGroupIPv4Index             INTEGER,
  mGuardFirewallGroupIPv4RowStatus         RowStatus,
  mGuardFirewallGroupIPv4Name              DisplayString,
  mGuardFirewallGroupIPv4Comment           DisplayString
}

-- FW_GROUP_IP table index
mGuardFirewallGroupIPv4Index OBJECT-TYPE
  SYNTAX INTEGER (1..2147483647)
  ACCESS not-accessible
  STATUS mandatory
  DESCRIPTION
    "Index to FW_GROUP_IP"
  ::= { mGuardFirewallGroupIPv4Entry 1 }

-- FW_GROUP_IP row status
mGuardFirewallGroupIPv4RowStatus OBJECT-TYPE
  SYNTAX RowStatus
  ACCESS read-write
  STATUS mandatory
  DESCRIPTION
    "RowStatus of FW_GROUP_IP"
  ::= { mGuardFirewallGroupIPv4Entry 2 }

-- FW_GROUP_IP.COMMENT
mGuardFirewallGroupIPv4Comment OBJECT-TYPE
  SYNTAX DisplayString
  ACCESS read-write
  STATUS mandatory
  DESCRIPTION
    "Variable name: FW_GROUP_IP.COMMENT
    WebUi Label: Comment
    Commentary or name for this IPv4 group."
  ::= { mGuardFirewallGroupIPv4Entry 4 }


-- FW_GROUP_IP.ENTRY table
mGuardFirewallGroupIPv4SingleTable OBJECT-TYPE
  SYNTAX SEQUENCE OF MGuardFirewallGroupIPv4SingleEntry
  ACCESS not-accessible
  STATUS mandatory
  DESCRIPTION
    "A table of FW_GROUP_IP.ENTRY"
  ::= { mGuardFirewallGroupIPv4 2 }

-- FW_GROUP_IP.ENTRY table entry
mGuardFirewallGroupIPv4SingleEntry OBJECT-TYPE
  SYNTAX MGuardFirewallGroupIPv4SingleEntry
  ACCESS not-accessible
  STATUS mandatory
  DESCRIPTION
    "An entry of FW_GROUP_IP.ENTRY"
  INDEX { mGuardFirewallGroupIPv4Index, mGuardFirewallGroupIPv4SingleIndex }
  ::= { mGuardFirewallGroupIPv4SingleTable 1 }

MGuardFirewallGroupIPv4SingleEntry ::= SEQUENCE {
  mGuardFirewallGroupIPv4SingleIndex       INTEGER,
  mGuardFirewallGroupIPv4SingleRowStatus   RowStatus,
  mGuardFirewallGroupIPv4SingleIP          DisplayString
}

-- FW_GROUP_IP.ENTRY table index
mGuardFirewallGroupIPv4SingleIndex OBJECT-TYPE
  SYNTAX INTEGER (1..2147483647)
  ACCESS not-accessible
  STATUS mandatory
  DESCRIPTION
    "Index to FW_GROUP_IP.ENTRY"
  ::= { mGuardFirewallGroupIPv4SingleEntry 1 }

-- FW_GROUP_IP.ENTRY row status
mGuardFirewallGroupIPv4SingleRowStatus OBJECT-TYPE
  SYNTAX RowStatus
  ACCESS read-write
  STATUS mandatory
  DESCRIPTION
    "RowStatus of FW_GROUP_IP.ENTRY"
  ::= { mGuardFirewallGroupIPv4SingleEntry 2 }

-- FW_GROUP_IP.ENTRY.IP
mGuardFirewallGroupIPv4SingleIP OBJECT-TYPE
  SYNTAX DisplayString
  ACCESS read-write
  STATUS mandatory
  DESCRIPTION
    "Variable name: FW_GROUP_IP.ENTRY.IP
    WebUi Label: Hostname, IP, IP range or network
    Hostname, IPv4 address, IPv4 network or IPv4 range"
  ::= { mGuardFirewallGroupIPv4SingleEntry 3 }

-- FW_GROUP_IP.NAME
mGuardFirewallGroupIPv4Name OBJECT-TYPE
  SYNTAX DisplayString
  ACCESS read-write
  STATUS mandatory
  DESCRIPTION
    "Variable name: FW_GROUP_IP.NAME
    WebUi Label: Name
    Name of the IPv4 group"
  ::= { mGuardFirewallGroupIPv4Entry 3 }


-- FW_GROUP_PORT table
mGuardFirewallGroupPortTable OBJECT-TYPE
  SYNTAX SEQUENCE OF MGuardFirewallGroupPortEntry
  ACCESS not-accessible
  STATUS mandatory
  DESCRIPTION
    "A table of FW_GROUP_PORT"
  ::= { mGuardFirewallGroupPort 1 }

-- FW_GROUP_PORT table entry
mGuardFirewallGroupPortEntry OBJECT-TYPE
  SYNTAX MGuardFirewallGroupPortEntry
  ACCESS not-accessible
  STATUS mandatory
  DESCRIPTION
    "An entry of FW_GROUP_PORT"
  INDEX { mGuardFirewallGroupPortIndex }
  ::= { mGuardFirewallGroupPortTable 1 }

MGuardFirewallGroupPortEntry ::= SEQUENCE {
  mGuardFirewallGroupPortIndex             INTEGER,
  mGuardFirewallGroupPortRowStatus         RowStatus,
  mGuardFirewallGroupPortName              DisplayString,
  mGuardFirewallGroupPortComment           DisplayString
}

-- FW_GROUP_PORT table index
mGuardFirewallGroupPortIndex OBJECT-TYPE
  SYNTAX INTEGER (1..2147483647)
  ACCESS not-accessible
  STATUS mandatory
  DESCRIPTION
    "Index to FW_GROUP_PORT"
  ::= { mGuardFirewallGroupPortEntry 1 }

-- FW_GROUP_PORT row status
mGuardFirewallGroupPortRowStatus OBJECT-TYPE
  SYNTAX RowStatus
  ACCESS read-write
  STATUS mandatory
  DESCRIPTION
    "RowStatus of FW_GROUP_PORT"
  ::= { mGuardFirewallGroupPortEntry 2 }

-- FW_GROUP_PORT.COMMENT
mGuardFirewallGroupPortComment OBJECT-TYPE
  SYNTAX DisplayString
  ACCESS read-write
  STATUS mandatory
  DESCRIPTION
    "Variable name: FW_GROUP_PORT.COMMENT
    WebUi Label: Comment
    Commentary or name for this service/port group."
  ::= { mGuardFirewallGroupPortEntry 4 }


-- FW_GROUP_PORT.ENTRY table
mGuardFirewallGroupPortSingleTable OBJECT-TYPE
  SYNTAX SEQUENCE OF MGuardFirewallGroupPortSingleEntry
  ACCESS not-accessible
  STATUS mandatory
  DESCRIPTION
    "A table of FW_GROUP_PORT.ENTRY"
  ::= { mGuardFirewallGroupPort 2 }

-- FW_GROUP_PORT.ENTRY table entry
mGuardFirewallGroupPortSingleEntry OBJECT-TYPE
  SYNTAX MGuardFirewallGroupPortSingleEntry
  ACCESS not-accessible
  STATUS mandatory
  DESCRIPTION
    "An entry of FW_GROUP_PORT.ENTRY"
  INDEX { mGuardFirewallGroupPortIndex, mGuardFirewallGroupPortSingleIndex }
  ::= { mGuardFirewallGroupPortSingleTable 1 }

MGuardFirewallGroupPortSingleEntry ::= SEQUENCE {
  mGuardFirewallGroupPortSingleIndex       INTEGER,
  mGuardFirewallGroupPortSingleRowStatus   RowStatus,
  mGuardFirewallGroupPortSingleIP          DisplayString
}

-- FW_GROUP_PORT.ENTRY table index
mGuardFirewallGroupPortSingleIndex OBJECT-TYPE
  SYNTAX INTEGER (1..2147483647)
  ACCESS not-accessible
  STATUS mandatory
  DESCRIPTION
    "Index to FW_GROUP_PORT.ENTRY"
  ::= { mGuardFirewallGroupPortSingleEntry 1 }

-- FW_GROUP_PORT.ENTRY row status
mGuardFirewallGroupPortSingleRowStatus OBJECT-TYPE
  SYNTAX RowStatus
  ACCESS read-write
  STATUS mandatory
  DESCRIPTION
    "RowStatus of FW_GROUP_PORT.ENTRY"
  ::= { mGuardFirewallGroupPortSingleEntry 2 }

-- FW_GROUP_PORT.ENTRY.PORT
mGuardFirewallGroupPortSingleIP OBJECT-TYPE
  SYNTAX DisplayString
  ACCESS read-write
  STATUS mandatory
  DESCRIPTION
    "Variable name: FW_GROUP_PORT.ENTRY.PORT
    WebUi Label: Port or port range
    Service name, port number or port range"
  ::= { mGuardFirewallGroupPortSingleEntry 3 }

-- FW_GROUP_PORT.NAME
mGuardFirewallGroupPortName OBJECT-TYPE
  SYNTAX DisplayString
  ACCESS read-write
  STATUS mandatory
  DESCRIPTION
    "Variable name: FW_GROUP_PORT.NAME
    WebUi Label: Name
    Name of the service/port group"
  ::= { mGuardFirewallGroupPortEntry 3 }

-- FW_ICMP
mGuardFirewallICMPPolicy OBJECT-TYPE
  SYNTAX INTEGER {
    drop(1),
    ping(2),
    all(3)
  }
  ACCESS read-write
  STATUS mandatory
  DESCRIPTION
    "Variable name: FW_ICMP
    WebUi Label: ICMP via primary external interface for the mGuard
    Allow incoming ICMP frames to the firewall itself (router modes only):
    drop: default, ping: allow incoming ICMP echo request (required to
    answer ping), all: allow all incoming ICMP request to reach the TCP
    stack. Note: ICMP packets related to established connections are
    handled by the connection tracking. This setting is used for unrelated
    ICMP traffic."
  ::= { mGuardFirewallExtended 11 }

-- FW_ICMP_DMZ0
mGuardFirewallICMPPolicyDmz0 OBJECT-TYPE
  SYNTAX INTEGER {
    drop(1),
    ping(2),
    all(3)
  }
  ACCESS read-write
  STATUS mandatory
  DESCRIPTION
    "Variable name: FW_ICMP_DMZ0
    WebUi Label: ICMP via DMZ interface for the mGuard
    Allow incoming ICMP frames to the firewall itself on the DMZ interface
    (router modes only): drop: default, ping: allow incoming ICMP echo
    request (required to answer ping), all: allow all incoming ICMP
    request to reach the TCP stack. Note: ICMP packets related to
    established connections are handled by the connection tracking. This
    setting is used for unrelated ICMP traffic."
  ::= { mGuardFirewallExtended 22 }

-- FW_ICMP_EXT2
mGuardFirewallICMPPolicy2 OBJECT-TYPE
  SYNTAX INTEGER {
    drop(1),
    ping(2),
    all(3)
  }
  ACCESS read-write
  STATUS mandatory
  DESCRIPTION
    "Variable name: FW_ICMP_EXT2
    WebUi Label: ICMP via secondary external interface for the mGuard
    Allow incoming ICMP frames to the firewall itself (on secondary
    external interface): drop: default, ping: allow incoming ICMP echo
    request (required to answer ping), all: allow all incoming ICMP
    request to reach the TCP stack. Note: ICMP packets related to
    established connections are handled by the connection tracking. This
    setting is used for unrelated ICMP traffic."
  ::= { mGuardFirewallExtended 19 }

-- FW_INCOMING
mGuardFirewallINuuid OBJECT-TYPE
  SYNTAX DisplayString
  ACCESS read-only
  STATUS mandatory
  DESCRIPTION
    "Variable name: FW_INCOMING
    WebUi Label: --
    Universally Unique Identifier (UUID, RFC 4122) used for
    mGuardFirewallIncomingTable logging."
  ::= { mGuardFirewallIncoming 3 }


-- FW_INCOMING table
mGuardFirewallIncomingTable OBJECT-TYPE
  SYNTAX SEQUENCE OF MGuardFirewallIncomingEntry
  ACCESS not-accessible
  STATUS mandatory
  DESCRIPTION
    "A table of FW_INCOMING"
  ::= { mGuardFirewallIncoming 1 }

-- FW_INCOMING table entry
mGuardFirewallIncomingEntry OBJECT-TYPE
  SYNTAX MGuardFirewallIncomingEntry
  ACCESS not-accessible
  STATUS mandatory
  DESCRIPTION
    "An entry of FW_INCOMING"
  INDEX { mGuardFWINruleIndex }
  ::= { mGuardFirewallIncomingTable 1 }

MGuardFirewallIncomingEntry ::= SEQUENCE {
  mGuardFWINruleIndex                      INTEGER,
  mGuardFWINproto                          INTEGER,
  mGuardFWINlog                            INTEGER,
  mGuardFWINRowStatus                      RowStatus,
  mGuardFWINcomment                        DisplayString,
  mGuardFWINfromMAC                        MacAddress,
  mGuardFWINExtIface                       INTEGER,
  mGuardFWINtargetOrRuleValue              INTEGER,
  mGuardFWINtargetOrRuleRef                OBJECT IDENTIFIER,
  mGuardFWINsourceIPOrGroupValue           DisplayString,
  mGuardFWINsourceIPOrGroupRef             OBJECT IDENTIFIER,
  mGuardFWINdestinationIPOrGroupValue      DisplayString,
  mGuardFWINdestinationIPOrGroupRef        OBJECT IDENTIFIER,
  mGuardFWINsportOrGroupValue              DisplayString,
  mGuardFWINsportOrGroupRef                OBJECT IDENTIFIER,
  mGuardFWINdportOrGroupValue              DisplayString,
  mGuardFWINdportOrGroupRef                OBJECT IDENTIFIER
}

-- FW_INCOMING table index
mGuardFWINruleIndex OBJECT-TYPE
  SYNTAX INTEGER (1..2147483647)
  ACCESS not-accessible
  STATUS mandatory
  DESCRIPTION
    "Index to FW_INCOMING"
  ::= { mGuardFirewallIncomingEntry 1 }

-- FW_INCOMING row status
mGuardFWINRowStatus OBJECT-TYPE
  SYNTAX RowStatus
  ACCESS read-write
  STATUS mandatory
  DESCRIPTION
    "RowStatus of FW_INCOMING"
  ::= { mGuardFirewallIncomingEntry 9 }

-- FW_INCOMING.COMMENT
mGuardFWINcomment OBJECT-TYPE
  SYNTAX DisplayString
  ACCESS read-write
  STATUS mandatory
  DESCRIPTION
    "Variable name: FW_INCOMING.COMMENT
    WebUi Label: Comment
    Commentary or name for this rule."
  ::= { mGuardFirewallIncomingEntry 10 }

-- FW_INCOMING.FROM_PORT
mGuardFWINsportOrGroupValue OBJECT-TYPE
  SYNTAX DisplayString
  ACCESS read-write
  STATUS mandatory
  DESCRIPTION
    "Variable name: FW_INCOMING.FROM_PORT
    WebUi Label: From port
    The rule's source port"
  ::= { mGuardFirewallIncomingEntry 20 }

-- FW_INCOMING.FROM_PORT reference
mGuardFWINsportOrGroupRef OBJECT-TYPE
  SYNTAX OBJECT IDENTIFIER
  ACCESS read-write
  STATUS mandatory
  DESCRIPTION
    "Variable name: FW_INCOMING.FROM_PORT
    WebUi Label: From port
    The rule's source port as reference to port group"
  ::= { mGuardFirewallIncomingEntry 21 }

-- FW_INCOMING.LOG
mGuardFWINlog OBJECT-TYPE
  SYNTAX INTEGER {
    yes(1),
    no(2)
  }
  ACCESS read-write
  STATUS mandatory
  DESCRIPTION
    "Variable name: FW_INCOMING.LOG
    WebUi Label: Log
    Log packets matching this rule ?"
  ::= { mGuardFirewallIncomingEntry 8 }

-- FW_INCOMING.EXT_IF
mGuardFWINExtIface OBJECT-TYPE
  SYNTAX INTEGER {
    extern(1),
    extern2(3),
    extern-all(1000)
  }
  ACCESS read-write
  STATUS mandatory
  DESCRIPTION
    "Variable name: FW_INCOMING.EXT_IF
    WebUi Label: Interface
    The incoming interface"
  ::= { mGuardFirewallIncomingEntry 13 }

-- FW_INCOMING.FROM_IP
mGuardFWINsourceIPOrGroupValue OBJECT-TYPE
  SYNTAX DisplayString
  ACCESS read-write
  STATUS mandatory
  DESCRIPTION
    "Variable name: FW_INCOMING.FROM_IP
    WebUi Label: From IP
    The rule's source IP address"
  ::= { mGuardFirewallIncomingEntry 16 }

-- FW_INCOMING.FROM_IP reference
mGuardFWINsourceIPOrGroupRef OBJECT-TYPE
  SYNTAX OBJECT IDENTIFIER
  ACCESS read-write
  STATUS mandatory
  DESCRIPTION
    "Variable name: FW_INCOMING.FROM_IP
    WebUi Label: From IP
    The rule's source IP address as reference to IP group"
  ::= { mGuardFirewallIncomingEntry 17 }

-- FW_INCOMING.IN_IP
mGuardFWINdestinationIPOrGroupValue OBJECT-TYPE
  SYNTAX DisplayString
  ACCESS read-write
  STATUS mandatory
  DESCRIPTION
    "Variable name: FW_INCOMING.IN_IP
    WebUi Label: To IP
    The rule's destination IP address"
  ::= { mGuardFirewallIncomingEntry 18 }

-- FW_INCOMING.IN_IP reference
mGuardFWINdestinationIPOrGroupRef OBJECT-TYPE
  SYNTAX OBJECT IDENTIFIER
  ACCESS read-write
  STATUS mandatory
  DESCRIPTION
    "Variable name: FW_INCOMING.IN_IP
    WebUi Label: To IP
    The rule's destination IP address as reference to IP group"
  ::= { mGuardFirewallIncomingEntry 19 }

-- FW_INCOMING.TARGET_REF
mGuardFWINtargetOrRuleValue OBJECT-TYPE
  SYNTAX INTEGER {
    accept(1),
    reject(2),
    drop(3)
  }
  ACCESS read-write
  STATUS mandatory
  DESCRIPTION
    "Variable name: FW_INCOMING.TARGET_REF
    WebUi Label: Action
    This object is effective if and only if the
    'mGuardFWINtargetOrRuleRef' object contains the OID of this object.
    When this object is read, it always returns the one of the values
    'accept', 'reject' or 'drop' . When one of the values is written to
    this object, no firewall rule set is used."
  ::= { mGuardFirewallIncomingEntry 14 }

-- FW_INCOMING.TARGET_REF reference
mGuardFWINtargetOrRuleRef OBJECT-TYPE
  SYNTAX OBJECT IDENTIFIER
  ACCESS read-write
  STATUS mandatory
  DESCRIPTION
    "Variable name: FW_INCOMING.TARGET_REF
    WebUi Label: Action
    When this object contains the OID of an 'mGuardFWRuleIndex' object,
    the corresponding firewall rule record is used for this firewall rule.
    To select a firewall rule record in this manner, write the OID of the
    corresponding 'mGuardFWRuleIndex' object to this object. To disable
    this feature, set the 'mGuardFWINtargetOrRuleValue' object."
  ::= { mGuardFirewallIncomingEntry 15 }

-- FW_INCOMING.PROTO
mGuardFWINproto OBJECT-TYPE
  SYNTAX INTEGER {
    tcp(1),
    udp(2),
    icmp(3),
    all(4),
    gre(5)
  }
  ACCESS read-write
  STATUS mandatory
  DESCRIPTION
    "Variable name: FW_INCOMING.PROTO
    WebUi Label: Protocol
    The rule's transport protocol"
  ::= { mGuardFirewallIncomingEntry 7 }

-- FW_INCOMING.FROM_MAC
mGuardFWINfromMAC OBJECT-TYPE
  SYNTAX MacAddress
  ACCESS read-write
  STATUS mandatory
  DESCRIPTION
    "Variable name: FW_INCOMING.FROM_MAC
    WebUi Label: From MAC
    The rule's source MAC address."
  ::= { mGuardFirewallIncomingEntry 11 }

-- FW_INCOMING.IN_PORT
mGuardFWINdportOrGroupValue OBJECT-TYPE
  SYNTAX DisplayString
  ACCESS read-write
  STATUS mandatory
  DESCRIPTION
    "Variable name: FW_INCOMING.IN_PORT
    WebUi Label: To port
    The rule's destination port as reference to port group"
  ::= { mGuardFirewallIncomingEntry 22 }

-- FW_INCOMING.IN_PORT reference
mGuardFWINdportOrGroupRef OBJECT-TYPE
  SYNTAX OBJECT IDENTIFIER
  ACCESS read-write
  STATUS mandatory
  DESCRIPTION
    "Variable name: FW_INCOMING.IN_PORT
    WebUi Label: To port
    The rule's destination port"
  ::= { mGuardFirewallIncomingEntry 23 }

-- FW_INCOMING_DMZ_LAN
mGuardFirewallDLINuuid OBJECT-TYPE
  SYNTAX DisplayString
  ACCESS read-only
  STATUS mandatory
  DESCRIPTION
    "Variable name: FW_INCOMING_DMZ_LAN
    WebUi Label: --
    Universally Unique Identifier (UUID, RFC 4122) used for
    mGuardFirewallIncomingDmzLanTable logging."
  ::= { mGuardFirewallIncomingDmzLan 3 }


-- FW_INCOMING_DMZ_LAN table
mGuardFirewallIncomingDmzLanTable OBJECT-TYPE
  SYNTAX SEQUENCE OF MGuardFirewallIncomingDmzLanEntry
  ACCESS not-accessible
  STATUS mandatory
  DESCRIPTION
    "A table of FW_INCOMING_DMZ_LAN"
  ::= { mGuardFirewallIncomingDmzLan 1 }

-- FW_INCOMING_DMZ_LAN table entry
mGuardFirewallIncomingDmzLanEntry OBJECT-TYPE
  SYNTAX MGuardFirewallIncomingDmzLanEntry
  ACCESS not-accessible
  STATUS mandatory
  DESCRIPTION
    "An entry of FW_INCOMING_DMZ_LAN"
  INDEX { mGuardFWDLINruleIndex }
  ::= { mGuardFirewallIncomingDmzLanTable 1 }

MGuardFirewallIncomingDmzLanEntry ::= SEQUENCE {
  mGuardFWDLINruleIndex                    INTEGER,
  mGuardFWDLINproto                        INTEGER,
  mGuardFWDLINlog                          INTEGER,
  mGuardFWDLINRowStatus                    RowStatus,
  mGuardFWDLINcomment                      DisplayString,
  mGuardFWDLINfromMAC                      MacAddress,
  mGuardFWDLINtargetOrRuleValue            INTEGER,
  mGuardFWDLINtargetOrRuleRef              OBJECT IDENTIFIER,
  mGuardFWDLINsourceIPOrGroupValue         DisplayString,
  mGuardFWDLINsourceIPOrGroupRef           OBJECT IDENTIFIER,
  mGuardFWDLINdestinationIPOrGroupValue    DisplayString,
  mGuardFWDLINdestinationIPOrGroupRef      OBJECT IDENTIFIER,
  mGuardFWDLINsportOrGroupValue            DisplayString,
  mGuardFWDLINsportOrGroupRef              OBJECT IDENTIFIER,
  mGuardFWDLINdportOrGroupValue            DisplayString,
  mGuardFWDLINdportOrGroupRef              OBJECT IDENTIFIER
}

-- FW_INCOMING_DMZ_LAN table index
mGuardFWDLINruleIndex OBJECT-TYPE
  SYNTAX INTEGER (1..2147483647)
  ACCESS not-accessible
  STATUS mandatory
  DESCRIPTION
    "Index to FW_INCOMING_DMZ_LAN"
  ::= { mGuardFirewallIncomingDmzLanEntry 1 }

-- FW_INCOMING_DMZ_LAN row status
mGuardFWDLINRowStatus OBJECT-TYPE
  SYNTAX RowStatus
  ACCESS read-write
  STATUS mandatory
  DESCRIPTION
    "RowStatus of FW_INCOMING_DMZ_LAN"
  ::= { mGuardFirewallIncomingDmzLanEntry 9 }

-- FW_INCOMING_DMZ_LAN.COMMENT
mGuardFWDLINcomment OBJECT-TYPE
  SYNTAX DisplayString
  ACCESS read-write
  STATUS mandatory
  DESCRIPTION
    "Variable name: FW_INCOMING_DMZ_LAN.COMMENT
    WebUi Label: Comment
    Commentary or name for this rule."
  ::= { mGuardFirewallIncomingDmzLanEntry 10 }

-- FW_INCOMING_DMZ_LAN.FROM_PORT
mGuardFWDLINsportOrGroupValue OBJECT-TYPE
  SYNTAX DisplayString
  ACCESS read-write
  STATUS mandatory
  DESCRIPTION
    "Variable name: FW_INCOMING_DMZ_LAN.FROM_PORT
    WebUi Label: From port
    The rule's source port"
  ::= { mGuardFirewallIncomingDmzLanEntry 20 }

-- FW_INCOMING_DMZ_LAN.FROM_PORT reference
mGuardFWDLINsportOrGroupRef OBJECT-TYPE
  SYNTAX OBJECT IDENTIFIER
  ACCESS read-write
  STATUS mandatory
  DESCRIPTION
    "Variable name: FW_INCOMING_DMZ_LAN.FROM_PORT
    WebUi Label: From port
    The rule's source port as reference to port group"
  ::= { mGuardFirewallIncomingDmzLanEntry 21 }

-- FW_INCOMING_DMZ_LAN.LOG
mGuardFWDLINlog OBJECT-TYPE
  SYNTAX INTEGER {
    yes(1),
    no(2)
  }
  ACCESS read-write
  STATUS mandatory
  DESCRIPTION
    "Variable name: FW_INCOMING_DMZ_LAN.LOG
    WebUi Label: Log
    Log packets matching this rule ?"
  ::= { mGuardFirewallIncomingDmzLanEntry 8 }

-- FW_INCOMING_DMZ_LAN.PROTO
mGuardFWDLINproto OBJECT-TYPE
  SYNTAX INTEGER {
    tcp(1),
    udp(2),
    icmp(3),
    all(4),
    gre(5)
  }
  ACCESS read-write
  STATUS mandatory
  DESCRIPTION
    "Variable name: FW_INCOMING_DMZ_LAN.PROTO
    WebUi Label: Protocol
    The rule's transport protocol"
  ::= { mGuardFirewallIncomingDmzLanEntry 7 }

-- FW_INCOMING_DMZ_LAN.FROM_IP
mGuardFWDLINsourceIPOrGroupValue OBJECT-TYPE
  SYNTAX DisplayString
  ACCESS read-write
  STATUS mandatory
  DESCRIPTION
    "Variable name: FW_INCOMING_DMZ_LAN.FROM_IP
    WebUi Label: From IP
    The rule's source IP address"
  ::= { mGuardFirewallIncomingDmzLanEntry 16 }

-- FW_INCOMING_DMZ_LAN.FROM_IP reference
mGuardFWDLINsourceIPOrGroupRef OBJECT-TYPE
  SYNTAX OBJECT IDENTIFIER
  ACCESS read-write
  STATUS mandatory
  DESCRIPTION
    "Variable name: FW_INCOMING_DMZ_LAN.FROM_IP
    WebUi Label: From IP
    The rule's source IP address as reference to IP group"
  ::= { mGuardFirewallIncomingDmzLanEntry 17 }

-- FW_INCOMING_DMZ_LAN.IN_IP
mGuardFWDLINdestinationIPOrGroupValue OBJECT-TYPE
  SYNTAX DisplayString
  ACCESS read-write
  STATUS mandatory
  DESCRIPTION
    "Variable name: FW_INCOMING_DMZ_LAN.IN_IP
    WebUi Label: To IP
    The rule's destination IP address"
  ::= { mGuardFirewallIncomingDmzLanEntry 18 }

-- FW_INCOMING_DMZ_LAN.IN_IP reference
mGuardFWDLINdestinationIPOrGroupRef OBJECT-TYPE
  SYNTAX OBJECT IDENTIFIER
  ACCESS read-write
  STATUS mandatory
  DESCRIPTION
    "Variable name: FW_INCOMING_DMZ_LAN.IN_IP
    WebUi Label: To IP
    The rule's destination IP address as reference to IP group"
  ::= { mGuardFirewallIncomingDmzLanEntry 19 }

-- FW_INCOMING_DMZ_LAN.TARGET_REF
mGuardFWDLINtargetOrRuleValue OBJECT-TYPE
  SYNTAX INTEGER {
    accept(1),
    reject(2),
    drop(3)
  }
  ACCESS read-write
  STATUS mandatory
  DESCRIPTION
    "Variable name: FW_INCOMING_DMZ_LAN.TARGET_REF
    WebUi Label: Action
    This object is effective if and only if the
    'mGuardFWDLINtargetOrRuleRef' object contains the OID of this object.
    When this object is read, it always returns the one of the values
    'accept', 'reject' or 'drop' . When one of the values is written to
    this object, no firewall rule set is used."
  ::= { mGuardFirewallIncomingDmzLanEntry 14 }

-- FW_INCOMING_DMZ_LAN.TARGET_REF reference
mGuardFWDLINtargetOrRuleRef OBJECT-TYPE
  SYNTAX OBJECT IDENTIFIER
  ACCESS read-write
  STATUS mandatory
  DESCRIPTION
    "Variable name: FW_INCOMING_DMZ_LAN.TARGET_REF
    WebUi Label: Action
    When this object contains the OID of an 'mGuardFWRuleIndex' object,
    the corresponding firewall rule record is used for this firewall rule.
    To select a firewall rule record in this manner, write the OID of the
    corresponding 'mGuardFWRuleIndex' object to this object. To disable
    this feature, set the 'mGuardFWDLINtargetOrRuleValue' object."
  ::= { mGuardFirewallIncomingDmzLanEntry 15 }

-- FW_INCOMING_DMZ_LAN.FROM_MAC
mGuardFWDLINfromMAC OBJECT-TYPE
  SYNTAX MacAddress
  ACCESS read-write
  STATUS mandatory
  DESCRIPTION
    "Variable name: FW_INCOMING_DMZ_LAN.FROM_MAC
    WebUi Label: From MAC
    The rule's source MAC address."
  ::= { mGuardFirewallIncomingDmzLanEntry 11 }

-- FW_INCOMING_DMZ_LAN.IN_PORT
mGuardFWDLINdportOrGroupValue OBJECT-TYPE
  SYNTAX DisplayString
  ACCESS read-write
  STATUS mandatory
  DESCRIPTION
    "Variable name: FW_INCOMING_DMZ_LAN.IN_PORT
    WebUi Label: To port
    The rule's destination port"
  ::= { mGuardFirewallIncomingDmzLanEntry 22 }

-- FW_INCOMING_DMZ_LAN.IN_PORT reference
mGuardFWDLINdportOrGroupRef OBJECT-TYPE
  SYNTAX OBJECT IDENTIFIER
  ACCESS read-write
  STATUS mandatory
  DESCRIPTION
    "Variable name: FW_INCOMING_DMZ_LAN.IN_PORT
    WebUi Label: To port
    The rule's destination port as reference to port group"
  ::= { mGuardFirewallIncomingDmzLanEntry 23 }

-- FW_INCOMING_GLOBAL
mGuardFirewallINGlobal OBJECT-TYPE
  SYNTAX INTEGER {
    accept(1),
    drop(2),
    rules(3),
    ping(4)
  }
  ACCESS read-write
  STATUS mandatory
  DESCRIPTION
    "Variable name: FW_INCOMING_GLOBAL
    WebUi Label: General firewall setting
    Global switch to accept or drop all connections or to follow the
    explicit firewall rules"
  ::= { mGuardFirewallIncoming 4 }

-- FW_INCOMING_WAN_DMZ
mGuardFirewallWDINuuid OBJECT-TYPE
  SYNTAX DisplayString
  ACCESS read-only
  STATUS mandatory
  DESCRIPTION
    "Variable name: FW_INCOMING_WAN_DMZ
    WebUi Label: --
    Universally Unique Identifier (UUID, RFC 4122) used for
    mGuardFirewallIncomingWanDmzTable logging."
  ::= { mGuardFirewallIncomingWanDmz 3 }


-- FW_INCOMING_WAN_DMZ table
mGuardFirewallIncomingWanDmzTable OBJECT-TYPE
  SYNTAX SEQUENCE OF MGuardFirewallIncomingWanDmzEntry
  ACCESS not-accessible
  STATUS mandatory
  DESCRIPTION
    "A table of FW_INCOMING_WAN_DMZ"
  ::= { mGuardFirewallIncomingWanDmz 1 }

-- FW_INCOMING_WAN_DMZ table entry
mGuardFirewallIncomingWanDmzEntry OBJECT-TYPE
  SYNTAX MGuardFirewallIncomingWanDmzEntry
  ACCESS not-accessible
  STATUS mandatory
  DESCRIPTION
    "An entry of FW_INCOMING_WAN_DMZ"
  INDEX { mGuardFWWDINruleIndex }
  ::= { mGuardFirewallIncomingWanDmzTable 1 }

MGuardFirewallIncomingWanDmzEntry ::= SEQUENCE {
  mGuardFWWDINruleIndex                    INTEGER,
  mGuardFWWDINproto                        INTEGER,
  mGuardFWWDINlog                          INTEGER,
  mGuardFWWDINRowStatus                    RowStatus,
  mGuardFWWDINcomment                      DisplayString,
  mGuardFWWDINfromMAC                      MacAddress,
  mGuardFWWDINExtIface                     INTEGER,
  mGuardFWWDINtargetOrRuleValue            INTEGER,
  mGuardFWWDINtargetOrRuleRef              OBJECT IDENTIFIER,
  mGuardFWWDINsourceIPOrGroupValue         DisplayString,
  mGuardFWWDINsourceIPOrGroupRef           OBJECT IDENTIFIER,
  mGuardFWWDINdestinationIPOrGroupValue    DisplayString,
  mGuardFWWDINdestinationIPOrGroupRef      OBJECT IDENTIFIER,
  mGuardFWWDINsportOrGroupValue            DisplayString,
  mGuardFWWDINsportOrGroupRef              OBJECT IDENTIFIER,
  mGuardFWWDINdportOrGroupValue            DisplayString,
  mGuardFWWDINdportOrGroupRef              OBJECT IDENTIFIER
}

-- FW_INCOMING_WAN_DMZ table index
mGuardFWWDINruleIndex OBJECT-TYPE
  SYNTAX INTEGER (1..2147483647)
  ACCESS not-accessible
  STATUS mandatory
  DESCRIPTION
    "Index to FW_INCOMING_WAN_DMZ"
  ::= { mGuardFirewallIncomingWanDmzEntry 1 }

-- FW_INCOMING_WAN_DMZ row status
mGuardFWWDINRowStatus OBJECT-TYPE
  SYNTAX RowStatus
  ACCESS read-write
  STATUS mandatory
  DESCRIPTION
    "RowStatus of FW_INCOMING_WAN_DMZ"
  ::= { mGuardFirewallIncomingWanDmzEntry 9 }

-- FW_INCOMING_WAN_DMZ.COMMENT
mGuardFWWDINcomment OBJECT-TYPE
  SYNTAX DisplayString
  ACCESS read-write
  STATUS mandatory
  DESCRIPTION
    "Variable name: FW_INCOMING_WAN_DMZ.COMMENT
    WebUi Label: Comment
    Commentary or name for this rule."
  ::= { mGuardFirewallIncomingWanDmzEntry 10 }

-- FW_INCOMING_WAN_DMZ.FROM_PORT
mGuardFWWDINsportOrGroupValue OBJECT-TYPE
  SYNTAX DisplayString
  ACCESS read-write
  STATUS mandatory
  DESCRIPTION
    "Variable name: FW_INCOMING_WAN_DMZ.FROM_PORT
    WebUi Label: From port
    The rule's source port"
  ::= { mGuardFirewallIncomingWanDmzEntry 20 }

-- FW_INCOMING_WAN_DMZ.FROM_PORT reference
mGuardFWWDINsportOrGroupRef OBJECT-TYPE
  SYNTAX OBJECT IDENTIFIER
  ACCESS read-write
  STATUS mandatory
  DESCRIPTION
    "Variable name: FW_INCOMING_WAN_DMZ.FROM_PORT
    WebUi Label: From port
    The rule's source port as reference to port group"
  ::= { mGuardFirewallIncomingWanDmzEntry 21 }

-- FW_INCOMING_WAN_DMZ.LOG
mGuardFWWDINlog OBJECT-TYPE
  SYNTAX INTEGER {
    yes(1),
    no(2)
  }
  ACCESS read-write
  STATUS mandatory
  DESCRIPTION
    "Variable name: FW_INCOMING_WAN_DMZ.LOG
    WebUi Label: Log
    Log packets matching this rule ?"
  ::= { mGuardFirewallIncomingWanDmzEntry 8 }

-- FW_INCOMING_WAN_DMZ.EXT_IF
mGuardFWWDINExtIface OBJECT-TYPE
  SYNTAX INTEGER {
    extern(1),
    extern2(3),
    extern-all(1000)
  }
  ACCESS read-write
  STATUS mandatory
  DESCRIPTION
    "Variable name: FW_INCOMING_WAN_DMZ.EXT_IF
    WebUi Label: Interface
    The incoming interface"
  ::= { mGuardFirewallIncomingWanDmzEntry 13 }

-- FW_INCOMING_WAN_DMZ.FROM_IP
mGuardFWWDINsourceIPOrGroupValue OBJECT-TYPE
  SYNTAX DisplayString
  ACCESS read-write
  STATUS mandatory
  DESCRIPTION
    "Variable name: FW_INCOMING_WAN_DMZ.FROM_IP
    WebUi Label: From IP
    The rule's source IP address"
  ::= { mGuardFirewallIncomingWanDmzEntry 16 }

-- FW_INCOMING_WAN_DMZ.FROM_IP reference
mGuardFWWDINsourceIPOrGroupRef OBJECT-TYPE
  SYNTAX OBJECT IDENTIFIER
  ACCESS read-write
  STATUS mandatory
  DESCRIPTION
    "Variable name: FW_INCOMING_WAN_DMZ.FROM_IP
    WebUi Label: From IP
    The rule's source IP address as reference to IP group"
  ::= { mGuardFirewallIncomingWanDmzEntry 17 }

-- FW_INCOMING_WAN_DMZ.IN_IP
mGuardFWWDINdestinationIPOrGroupValue OBJECT-TYPE
  SYNTAX DisplayString
  ACCESS read-write
  STATUS mandatory
  DESCRIPTION
    "Variable name: FW_INCOMING_WAN_DMZ.IN_IP
    WebUi Label: To IP
    The rule's destination IP address"
  ::= { mGuardFirewallIncomingWanDmzEntry 18 }

-- FW_INCOMING_WAN_DMZ.IN_IP reference
mGuardFWWDINdestinationIPOrGroupRef OBJECT-TYPE
  SYNTAX OBJECT IDENTIFIER
  ACCESS read-write
  STATUS mandatory
  DESCRIPTION
    "Variable name: FW_INCOMING_WAN_DMZ.IN_IP
    WebUi Label: To IP
    The rule's destination IP address as reference to IP group"
  ::= { mGuardFirewallIncomingWanDmzEntry 19 }

-- FW_INCOMING_WAN_DMZ.TARGET_REF
mGuardFWWDINtargetOrRuleValue OBJECT-TYPE
  SYNTAX INTEGER {
    accept(1),
    reject(2),
    drop(3)
  }
  ACCESS read-write
  STATUS mandatory
  DESCRIPTION
    "Variable name: FW_INCOMING_WAN_DMZ.TARGET_REF
    WebUi Label: Action
    This object is effective if and only if the
    'mGuardFWWDINtargetOrRuleRef' object contains the OID of this object.
    When this object is read, it always returns the one of the values
    'accept', 'reject' or 'drop' . When one of the values is written to
    this object, no firewall rule set is used."
  ::= { mGuardFirewallIncomingWanDmzEntry 14 }

-- FW_INCOMING_WAN_DMZ.TARGET_REF reference
mGuardFWWDINtargetOrRuleRef OBJECT-TYPE
  SYNTAX OBJECT IDENTIFIER
  ACCESS read-write
  STATUS mandatory
  DESCRIPTION
    "Variable name: FW_INCOMING_WAN_DMZ.TARGET_REF
    WebUi Label: Action
    When this object contains the OID of an 'mGuardFWRuleIndex' object,
    the corresponding firewall rule record is used for this firewall rule.
    To select a firewall rule record in this manner, write the OID of the
    corresponding 'mGuardFWRuleIndex' object to this object. To disable
    this feature, set the 'mGuardFWWDINtargetOrRuleValue' object."
  ::= { mGuardFirewallIncomingWanDmzEntry 15 }

-- FW_INCOMING_WAN_DMZ.PROTO
mGuardFWWDINproto OBJECT-TYPE
  SYNTAX INTEGER {
    tcp(1),
    udp(2),
    icmp(3),
    all(4),
    gre(5)
  }
  ACCESS read-write
  STATUS mandatory
  DESCRIPTION
    "Variable name: FW_INCOMING_WAN_DMZ.PROTO
    WebUi Label: Protocol
    The rule's transport protocol"
  ::= { mGuardFirewallIncomingWanDmzEntry 7 }

-- FW_INCOMING_WAN_DMZ.FROM_MAC
mGuardFWWDINfromMAC OBJECT-TYPE
  SYNTAX MacAddress
  ACCESS read-write
  STATUS mandatory
  DESCRIPTION
    "Variable name: FW_INCOMING_WAN_DMZ.FROM_MAC
    WebUi Label: From MAC
    The rule's source MAC address."
  ::= { mGuardFirewallIncomingWanDmzEntry 11 }

-- FW_INCOMING_WAN_DMZ.IN_PORT
mGuardFWWDINdportOrGroupValue OBJECT-TYPE
  SYNTAX DisplayString
  ACCESS read-write
  STATUS mandatory
  DESCRIPTION
    "Variable name: FW_INCOMING_WAN_DMZ.IN_PORT
    WebUi Label: To port
    The rule's destination port"
  ::= { mGuardFirewallIncomingWanDmzEntry 22 }

-- FW_INCOMING_WAN_DMZ.IN_PORT reference
mGuardFWWDINdportOrGroupRef OBJECT-TYPE
  SYNTAX OBJECT IDENTIFIER
  ACCESS read-write
  STATUS mandatory
  DESCRIPTION
    "Variable name: FW_INCOMING_WAN_DMZ.IN_PORT
    WebUi Label: To port
    The rule's destination port as reference to port group"
  ::= { mGuardFirewallIncomingWanDmzEntry 23 }


-- FW_NAT table
mGuardFirewallNATRuleTable OBJECT-TYPE
  SYNTAX SEQUENCE OF MGuardFirewallNATRuleEntry
  ACCESS not-accessible
  STATUS mandatory
  DESCRIPTION
    "A table of FW_NAT"
  ::= { mGuardFirewallNAT 1 }

-- FW_NAT table entry
mGuardFirewallNATRuleEntry OBJECT-TYPE
  SYNTAX MGuardFirewallNATRuleEntry
  ACCESS not-accessible
  STATUS mandatory
  DESCRIPTION
    "An entry of FW_NAT"
  INDEX { mGuardFWNATruleIndex }
  ::= { mGuardFirewallNATRuleTable 1 }

MGuardFirewallNATRuleEntry ::= SEQUENCE {
  mGuardFWNATruleIndex                     INTEGER,
  mGuardFWNATRowStatus                     RowStatus,
  mGuardFWNATComment                       DisplayString,
  mGuardFWNATExtIface                      INTEGER,
  mGuardFWNATIPOrGroupValue                DisplayString,
  mGuardFWNATIPOrGroupRef                  OBJECT IDENTIFIER
}

-- FW_NAT table index
mGuardFWNATruleIndex OBJECT-TYPE
  SYNTAX INTEGER (1..2147483647)
  ACCESS not-accessible
  STATUS mandatory
  DESCRIPTION
    "Index to FW_NAT"
  ::= { mGuardFirewallNATRuleEntry 1 }

-- FW_NAT row status
mGuardFWNATRowStatus OBJECT-TYPE
  SYNTAX RowStatus
  ACCESS read-write
  STATUS mandatory
  DESCRIPTION
    "RowStatus of FW_NAT"
  ::= { mGuardFirewallNATRuleEntry 3 }

-- FW_NAT.COMMENT
mGuardFWNATComment OBJECT-TYPE
  SYNTAX DisplayString
  ACCESS read-write
  STATUS mandatory
  DESCRIPTION
    "Variable name: FW_NAT.COMMENT
    WebUi Label: Comment
    Commentary or name for this rule."
  ::= { mGuardFirewallNATRuleEntry 5 }

-- FW_NAT.IN_IP
mGuardFWNATIPOrGroupValue OBJECT-TYPE
  SYNTAX DisplayString
  ACCESS read-write
  STATUS mandatory
  DESCRIPTION
    "Variable name: FW_NAT.IN_IP
    WebUi Label: From IP
    The rule's source IP address"
  ::= { mGuardFirewallNATRuleEntry 16 }

-- FW_NAT.IN_IP reference
mGuardFWNATIPOrGroupRef OBJECT-TYPE
  SYNTAX OBJECT IDENTIFIER
  ACCESS read-write
  STATUS mandatory
  DESCRIPTION
    "Variable name: FW_NAT.IN_IP
    WebUi Label: From IP
    The rule's source IP address as reference to IP group"
  ::= { mGuardFirewallNATRuleEntry 17 }

-- FW_NAT.EXT_IF
mGuardFWNATExtIface OBJECT-TYPE
  SYNTAX INTEGER {
    extern(1),
    extern2(3),
    dmz0(5),
    extern-all(1000),
    intern(1010)
  }
  ACCESS read-write
  STATUS mandatory
  DESCRIPTION
    "Variable name: FW_NAT.EXT_IF
    WebUi Label: Outgoing on interface
    The incoming interface"
  ::= { mGuardFirewallNATRuleEntry 6 }

-- FW_NEW_CONNECTIONS_UPON_SYN_ONLY
mGuardFirewallConntrackReqTcpSyn OBJECT-TYPE
  SYNTAX INTEGER {
    yes(1),
    no(2)
  }
  ACCESS read-write
  STATUS mandatory
  DESCRIPTION
    "Variable name: FW_NEW_CONNECTIONS_UPON_SYN_ONLY
    WebUi Label: Allow TCP connections upon SYN only (After reboot connections need to
     be re-established.)
    Allow TCP connections upon SYN only (after reboot connections need to
    be re-established)"
  ::= { mGuardFirewallExtended 16 }

-- FW_OUTGOING
mGuardFirewallOUTuuid OBJECT-TYPE
  SYNTAX DisplayString
  ACCESS read-only
  STATUS mandatory
  DESCRIPTION
    "Variable name: FW_OUTGOING
    WebUi Label: --
    Universally Unique Identifier (UUID, RFC 4122) used for
    mGuardFirewallOutgoingTable logging."
  ::= { mGuardFirewallOutgoing 3 }


-- FW_OUTGOING table
mGuardFirewallOutgoingTable OBJECT-TYPE
  SYNTAX SEQUENCE OF MGuardFirewallOutgoingEntry
  ACCESS not-accessible
  STATUS mandatory
  DESCRIPTION
    "A table of FW_OUTGOING"
  ::= { mGuardFirewallOutgoing 1 }

-- FW_OUTGOING table entry
mGuardFirewallOutgoingEntry OBJECT-TYPE
  SYNTAX MGuardFirewallOutgoingEntry
  ACCESS not-accessible
  STATUS mandatory
  DESCRIPTION
    "An entry of FW_OUTGOING"
  INDEX { mGuardFWOUTruleIndex }
  ::= { mGuardFirewallOutgoingTable 1 }

MGuardFirewallOutgoingEntry ::= SEQUENCE {
  mGuardFWOUTruleIndex                     INTEGER,
  mGuardFWOUTproto                         INTEGER,
  mGuardFWOUTlog                           INTEGER,
  mGuardFWOUTRowStatus                     RowStatus,
  mGuardFWOUTcomment                       DisplayString,
  mGuardFWOUTfromMAC                       MacAddress,
  mGuardFWOUTtargetOrRuleValue             INTEGER,
  mGuardFWOUTtargetOrRuleRef               OBJECT IDENTIFIER,
  mGuardFWOUTsourceIPOrGroupValue          DisplayString,
  mGuardFWOUTsourceIPOrGroupRef            OBJECT IDENTIFIER,
  mGuardFWOUTdestinationIPOrGroupValue     DisplayString,
  mGuardFWOUTdestinationIPOrGroupRef       OBJECT IDENTIFIER,
  mGuardFWOUTsportOrGroupValue             DisplayString,
  mGuardFWOUTsportOrGroupRef               OBJECT IDENTIFIER,
  mGuardFWOUTdportOrGroupValue             DisplayString,
  mGuardFWOUTdportOrGroupRef               OBJECT IDENTIFIER
}

-- FW_OUTGOING table index
mGuardFWOUTruleIndex OBJECT-TYPE
  SYNTAX INTEGER (1..2147483647)
  ACCESS not-accessible
  STATUS mandatory
  DESCRIPTION
    "Index to FW_OUTGOING"
  ::= { mGuardFirewallOutgoingEntry 1 }

-- FW_OUTGOING row status
mGuardFWOUTRowStatus OBJECT-TYPE
  SYNTAX RowStatus
  ACCESS read-write
  STATUS mandatory
  DESCRIPTION
    "RowStatus of FW_OUTGOING"
  ::= { mGuardFirewallOutgoingEntry 9 }

-- FW_OUTGOING.COMMENT
mGuardFWOUTcomment OBJECT-TYPE
  SYNTAX DisplayString
  ACCESS read-write
  STATUS mandatory
  DESCRIPTION
    "Variable name: FW_OUTGOING.COMMENT
    WebUi Label: Comment
    Commentary or name for this rule."
  ::= { mGuardFirewallOutgoingEntry 10 }

-- FW_OUTGOING.FROM_PORT
mGuardFWOUTsportOrGroupValue OBJECT-TYPE
  SYNTAX DisplayString
  ACCESS read-write
  STATUS mandatory
  DESCRIPTION
    "Variable name: FW_OUTGOING.FROM_PORT
    WebUi Label: From port
    The rule's source port"
  ::= { mGuardFirewallOutgoingEntry 20 }

-- FW_OUTGOING.FROM_PORT reference
mGuardFWOUTsportOrGroupRef OBJECT-TYPE
  SYNTAX OBJECT IDENTIFIER
  ACCESS read-write
  STATUS mandatory
  DESCRIPTION
    "Variable name: FW_OUTGOING.FROM_PORT
    WebUi Label: From port
    The rule's source port as reference to port group"
  ::= { mGuardFirewallOutgoingEntry 21 }

-- FW_OUTGOING.LOG
mGuardFWOUTlog OBJECT-TYPE
  SYNTAX INTEGER {
    yes(1),
    no(2)
  }
  ACCESS read-write
  STATUS mandatory
  DESCRIPTION
    "Variable name: FW_OUTGOING.LOG
    WebUi Label: Log
    Log packets matching this rule ?"
  ::= { mGuardFirewallOutgoingEntry 8 }

-- FW_OUTGOING.PROTO
mGuardFWOUTproto OBJECT-TYPE
  SYNTAX INTEGER {
    tcp(1),
    udp(2),
    icmp(3),
    all(4),
    gre(5)
  }
  ACCESS read-write
  STATUS mandatory
  DESCRIPTION
    "Variable name: FW_OUTGOING.PROTO
    WebUi Label: Protocol
    The rule's transport protocol"
  ::= { mGuardFirewallOutgoingEntry 7 }

-- FW_OUTGOING.FROM_IP
mGuardFWOUTsourceIPOrGroupValue OBJECT-TYPE
  SYNTAX DisplayString
  ACCESS read-write
  STATUS mandatory
  DESCRIPTION
    "Variable name: FW_OUTGOING.FROM_IP
    WebUi Label: From IP
    The rule's source IP address"
  ::= { mGuardFirewallOutgoingEntry 16 }

-- FW_OUTGOING.FROM_IP reference
mGuardFWOUTsourceIPOrGroupRef OBJECT-TYPE
  SYNTAX OBJECT IDENTIFIER
  ACCESS read-write
  STATUS mandatory
  DESCRIPTION
    "Variable name: FW_OUTGOING.FROM_IP
    WebUi Label: From IP
    The rule's source IP address as reference to IP group"
  ::= { mGuardFirewallOutgoingEntry 17 }

-- FW_OUTGOING.IN_IP
mGuardFWOUTdestinationIPOrGroupValue OBJECT-TYPE
  SYNTAX DisplayString
  ACCESS read-write
  STATUS mandatory
  DESCRIPTION
    "Variable name: FW_OUTGOING.IN_IP
    WebUi Label: To IP
    The rule's destination IP address"
  ::= { mGuardFirewallOutgoingEntry 18 }

-- FW_OUTGOING.IN_IP reference
mGuardFWOUTdestinationIPOrGroupRef OBJECT-TYPE
  SYNTAX OBJECT IDENTIFIER
  ACCESS read-write
  STATUS mandatory
  DESCRIPTION
    "Variable name: FW_OUTGOING.IN_IP
    WebUi Label: To IP
    The rule's destination IP address as reference to IP group"
  ::= { mGuardFirewallOutgoingEntry 19 }

-- FW_OUTGOING.TARGET_REF
mGuardFWOUTtargetOrRuleValue OBJECT-TYPE
  SYNTAX INTEGER {
    accept(1),
    reject(2),
    drop(3)
  }
  ACCESS read-write
  STATUS mandatory
  DESCRIPTION
    "Variable name: FW_OUTGOING.TARGET_REF
    WebUi Label: Action
    This object is effective if and only if the
    'mGuardFWOUTtargetOrRuleRef' object contains the OID of this object.
    When this object is read, it always returns the one of the values
    'accept', 'reject' or 'drop' . When one of the values is written to
    this object, no firewall rule set is used."
  ::= { mGuardFirewallOutgoingEntry 13 }

-- FW_OUTGOING.TARGET_REF reference
mGuardFWOUTtargetOrRuleRef OBJECT-TYPE
  SYNTAX OBJECT IDENTIFIER
  ACCESS read-write
  STATUS mandatory
  DESCRIPTION
    "Variable name: FW_OUTGOING.TARGET_REF
    WebUi Label: Action
    When this object contains the OID of an 'mGuardFWRuleIndex' object,
    the corresponding firewall rule record is used for this firewall rule.
    To select a firewall rule record in this manner, write the OID of the
    corresponding 'mGuardFWRuleIndex' object to this object. To disable
    this feature, set the 'mGuardFWOUTtargetOrRuleValue' object."
  ::= { mGuardFirewallOutgoingEntry 14 }

-- FW_OUTGOING.FROM_MAC
mGuardFWOUTfromMAC OBJECT-TYPE
  SYNTAX MacAddress
  ACCESS read-write
  STATUS mandatory
  DESCRIPTION
    "Variable name: FW_OUTGOING.FROM_MAC
    WebUi Label: From MAC
    The rule's source MAC address."
  ::= { mGuardFirewallOutgoingEntry 11 }

-- FW_OUTGOING.IN_PORT
mGuardFWOUTdportOrGroupValue OBJECT-TYPE
  SYNTAX DisplayString
  ACCESS read-write
  STATUS mandatory
  DESCRIPTION
    "Variable name: FW_OUTGOING.IN_PORT
    WebUi Label: To port
    The rule's destination port"
  ::= { mGuardFirewallOutgoingEntry 22 }

-- FW_OUTGOING.IN_PORT reference
mGuardFWOUTdportOrGroupRef OBJECT-TYPE
  SYNTAX OBJECT IDENTIFIER
  ACCESS read-write
  STATUS mandatory
  DESCRIPTION
    "Variable name: FW_OUTGOING.IN_PORT
    WebUi Label: To port
    The rule's destination port as reference to port group"
  ::= { mGuardFirewallOutgoingEntry 23 }

-- FW_OUTGOING_DMZWAN
mGuardFirewallDWOUTuuid OBJECT-TYPE
  SYNTAX DisplayString
  ACCESS read-only
  STATUS mandatory
  DESCRIPTION
    "Variable name: FW_OUTGOING_DMZWAN
    WebUi Label: --
    Universally Unique Identifier (UUID, RFC 4122) used for
    mGuardFirewallOutgoingDmzWanTable logging."
  ::= { mGuardFirewallOutgoingDmzWan 3 }


-- FW_OUTGOING_DMZWAN table
mGuardFirewallOutgoingDmzWanTable OBJECT-TYPE
  SYNTAX SEQUENCE OF MGuardFirewallOutgoingDmzWanEntry
  ACCESS not-accessible
  STATUS mandatory
  DESCRIPTION
    "A table of FW_OUTGOING_DMZWAN"
  ::= { mGuardFirewallOutgoingDmzWan 1 }

-- FW_OUTGOING_DMZWAN table entry
mGuardFirewallOutgoingDmzWanEntry OBJECT-TYPE
  SYNTAX MGuardFirewallOutgoingDmzWanEntry
  ACCESS not-accessible
  STATUS mandatory
  DESCRIPTION
    "An entry of FW_OUTGOING_DMZWAN"
  INDEX { mGuardFWDWOUTruleIndex }
  ::= { mGuardFirewallOutgoingDmzWanTable 1 }

MGuardFirewallOutgoingDmzWanEntry ::= SEQUENCE {
  mGuardFWDWOUTruleIndex                   INTEGER,
  mGuardFWDWOUTproto                       INTEGER,
  mGuardFWDWOUTlog                         INTEGER,
  mGuardFWDWOUTRowStatus                   RowStatus,
  mGuardFWDWOUTcomment                     DisplayString,
  mGuardFWDWOUTfromMAC                     MacAddress,
  mGuardFWDWOUTtargetOrRuleValue           INTEGER,
  mGuardFWDWOUTtargetOrRuleRef             OBJECT IDENTIFIER,
  mGuardFWDWOUTsourceIPOrGroupValue        DisplayString,
  mGuardFWDWOUTsourceIPOrGroupRef          OBJECT IDENTIFIER,
  mGuardFWDWOUTdestinationIPOrGroupValue   DisplayString,
  mGuardFWDWOUTdestinationIPOrGroupRef     OBJECT IDENTIFIER,
  mGuardFWDWOUTsportOrGroupValue           DisplayString,
  mGuardFWDWOUTsportOrGroupRef             OBJECT IDENTIFIER,
  mGuardFWDWOUTdportOrGroupValue           DisplayString,
  mGuardFWDWOUTdportOrGroupRef             OBJECT IDENTIFIER
}

-- FW_OUTGOING_DMZWAN table index
mGuardFWDWOUTruleIndex OBJECT-TYPE
  SYNTAX INTEGER (1..2147483647)
  ACCESS not-accessible
  STATUS mandatory
  DESCRIPTION
    "Index to FW_OUTGOING_DMZWAN"
  ::= { mGuardFirewallOutgoingDmzWanEntry 1 }

-- FW_OUTGOING_DMZWAN row status
mGuardFWDWOUTRowStatus OBJECT-TYPE
  SYNTAX RowStatus
  ACCESS read-write
  STATUS mandatory
  DESCRIPTION
    "RowStatus of FW_OUTGOING_DMZWAN"
  ::= { mGuardFirewallOutgoingDmzWanEntry 9 }

-- FW_OUTGOING_DMZWAN.COMMENT
mGuardFWDWOUTcomment OBJECT-TYPE
  SYNTAX DisplayString
  ACCESS read-write
  STATUS mandatory
  DESCRIPTION
    "Variable name: FW_OUTGOING_DMZWAN.COMMENT
    WebUi Label: Comment
    Commentary or name for this rule."
  ::= { mGuardFirewallOutgoingDmzWanEntry 10 }

-- FW_OUTGOING_DMZWAN.FROM_PORT
mGuardFWDWOUTsportOrGroupValue OBJECT-TYPE
  SYNTAX DisplayString
  ACCESS read-write
  STATUS mandatory
  DESCRIPTION
    "Variable name: FW_OUTGOING_DMZWAN.FROM_PORT
    WebUi Label: From port
    The rule's source port"
  ::= { mGuardFirewallOutgoingDmzWanEntry 20 }

-- FW_OUTGOING_DMZWAN.FROM_PORT reference
mGuardFWDWOUTsportOrGroupRef OBJECT-TYPE
  SYNTAX OBJECT IDENTIFIER
  ACCESS read-write
  STATUS mandatory
  DESCRIPTION
    "Variable name: FW_OUTGOING_DMZWAN.FROM_PORT
    WebUi Label: From port
    The rule's source port as reference to port group"
  ::= { mGuardFirewallOutgoingDmzWanEntry 21 }

-- FW_OUTGOING_DMZWAN.LOG
mGuardFWDWOUTlog OBJECT-TYPE
  SYNTAX INTEGER {
    yes(1),
    no(2)
  }
  ACCESS read-write
  STATUS mandatory
  DESCRIPTION
    "Variable name: FW_OUTGOING_DMZWAN.LOG
    WebUi Label: Log
    Log packets matching this rule ?"
  ::= { mGuardFirewallOutgoingDmzWanEntry 8 }

-- FW_OUTGOING_DMZWAN.PROTO
mGuardFWDWOUTproto OBJECT-TYPE
  SYNTAX INTEGER {
    tcp(1),
    udp(2),
    icmp(3),
    all(4),
    gre(5)
  }
  ACCESS read-write
  STATUS mandatory
  DESCRIPTION
    "Variable name: FW_OUTGOING_DMZWAN.PROTO
    WebUi Label: Protocol
    The rule's transport protocol"
  ::= { mGuardFirewallOutgoingDmzWanEntry 7 }

-- FW_OUTGOING_DMZWAN.FROM_IP
mGuardFWDWOUTsourceIPOrGroupValue OBJECT-TYPE
  SYNTAX DisplayString
  ACCESS read-write
  STATUS mandatory
  DESCRIPTION
    "Variable name: FW_OUTGOING_DMZWAN.FROM_IP
    WebUi Label: From IP
    The rule's source IP address"
  ::= { mGuardFirewallOutgoingDmzWanEntry 16 }

-- FW_OUTGOING_DMZWAN.FROM_IP reference
mGuardFWDWOUTsourceIPOrGroupRef OBJECT-TYPE
  SYNTAX OBJECT IDENTIFIER
  ACCESS read-write
  STATUS mandatory
  DESCRIPTION
    "Variable name: FW_OUTGOING_DMZWAN.FROM_IP
    WebUi Label: From IP
    The rule's source IP address as reference to IP group"
  ::= { mGuardFirewallOutgoingDmzWanEntry 17 }

-- FW_OUTGOING_DMZWAN.IN_IP
mGuardFWDWOUTdestinationIPOrGroupValue OBJECT-TYPE
  SYNTAX DisplayString
  ACCESS read-write
  STATUS mandatory
  DESCRIPTION
    "Variable name: FW_OUTGOING_DMZWAN.IN_IP
    WebUi Label: To IP
    The rule's destination IP address"
  ::= { mGuardFirewallOutgoingDmzWanEntry 18 }

-- FW_OUTGOING_DMZWAN.IN_IP reference
mGuardFWDWOUTdestinationIPOrGroupRef OBJECT-TYPE
  SYNTAX OBJECT IDENTIFIER
  ACCESS read-write
  STATUS mandatory
  DESCRIPTION
    "Variable name: FW_OUTGOING_DMZWAN.IN_IP
    WebUi Label: To IP
    The rule's destination IP address as reference to IP group"
  ::= { mGuardFirewallOutgoingDmzWanEntry 19 }

-- FW_OUTGOING_DMZWAN.TARGET_REF
mGuardFWDWOUTtargetOrRuleValue OBJECT-TYPE
  SYNTAX INTEGER {
    accept(1),
    reject(2),
    drop(3)
  }
  ACCESS read-write
  STATUS mandatory
  DESCRIPTION
    "Variable name: FW_OUTGOING_DMZWAN.TARGET_REF
    WebUi Label: Action
    This object is effective if and only if the
    'mGuardFWDWOUTtargetOrRuleRef' object contains the OID of this object.
    When this object is read, it always returns the one of the values
    'accept', 'reject' or 'drop' . When one of the values is written to
    this object, no firewall rule set is used."
  ::= { mGuardFirewallOutgoingDmzWanEntry 14 }

-- FW_OUTGOING_DMZWAN.TARGET_REF reference
mGuardFWDWOUTtargetOrRuleRef OBJECT-TYPE
  SYNTAX OBJECT IDENTIFIER
  ACCESS read-write
  STATUS mandatory
  DESCRIPTION
    "Variable name: FW_OUTGOING_DMZWAN.TARGET_REF
    WebUi Label: Action
    When this object contains the OID of an 'mGuardFWRuleIndex' object,
    the corresponding firewall rule record is used for this firewall rule.
    To select a firewall rule record in this manner, write the OID of the
    corresponding 'mGuardFWRuleIndex' object to this object. To disable
    this feature, set the 'mGuardFWDWOUTtargetOrRuleValue' object."
  ::= { mGuardFirewallOutgoingDmzWanEntry 15 }

-- FW_OUTGOING_DMZWAN.FROM_MAC
mGuardFWDWOUTfromMAC OBJECT-TYPE
  SYNTAX MacAddress
  ACCESS read-write
  STATUS mandatory
  DESCRIPTION
    "Variable name: FW_OUTGOING_DMZWAN.FROM_MAC
    WebUi Label: From MAC
    The rule's source MAC address."
  ::= { mGuardFirewallOutgoingDmzWanEntry 11 }

-- FW_OUTGOING_DMZWAN.IN_PORT
mGuardFWDWOUTdportOrGroupValue OBJECT-TYPE
  SYNTAX DisplayString
  ACCESS read-write
  STATUS mandatory
  DESCRIPTION
    "Variable name: FW_OUTGOING_DMZWAN.IN_PORT
    WebUi Label: To port
    The rule's destination port"
  ::= { mGuardFirewallOutgoingDmzWanEntry 22 }

-- FW_OUTGOING_DMZWAN.IN_PORT reference
mGuardFWDWOUTdportOrGroupRef OBJECT-TYPE
  SYNTAX OBJECT IDENTIFIER
  ACCESS read-write
  STATUS mandatory
  DESCRIPTION
    "Variable name: FW_OUTGOING_DMZWAN.IN_PORT
    WebUi Label: To port
    The rule's destination port as reference to port group"
  ::= { mGuardFirewallOutgoingDmzWanEntry 23 }

-- FW_OUTGOING_GLOBAL
mGuardFirewallOUTGlobal OBJECT-TYPE
  SYNTAX INTEGER {
    accept(1),
    drop(2),
    rules(3),
    ping(4)
  }
  ACCESS read-write
  STATUS mandatory
  DESCRIPTION
    "Variable name: FW_OUTGOING_GLOBAL
    WebUi Label: General firewall setting
    Global switch to accept or drop all connections or to follow the
    explicit firewall rules"
  ::= { mGuardFirewallOutgoing 4 }

-- FW_OUTGOING_LANDMZ
mGuardFirewallLDOUTuuid OBJECT-TYPE
  SYNTAX DisplayString
  ACCESS read-only
  STATUS mandatory
  DESCRIPTION
    "Variable name: FW_OUTGOING_LANDMZ
    WebUi Label: --
    Universally Unique Identifier (UUID, RFC 4122) used for
    mGuardFirewallOutgoingLanDmzTable logging."
  ::= { mGuardFirewallOutgoingLanDmz 3 }


-- FW_OUTGOING_LANDMZ table
mGuardFirewallOutgoingLanDmzTable OBJECT-TYPE
  SYNTAX SEQUENCE OF MGuardFirewallOutgoingLanDmzEntry
  ACCESS not-accessible
  STATUS mandatory
  DESCRIPTION
    "A table of FW_OUTGOING_LANDMZ"
  ::= { mGuardFirewallOutgoingLanDmz 1 }

-- FW_OUTGOING_LANDMZ table entry
mGuardFirewallOutgoingLanDmzEntry OBJECT-TYPE
  SYNTAX MGuardFirewallOutgoingLanDmzEntry
  ACCESS not-accessible
  STATUS mandatory
  DESCRIPTION
    "An entry of FW_OUTGOING_LANDMZ"
  INDEX { mGuardFWLDOUTruleIndex }
  ::= { mGuardFirewallOutgoingLanDmzTable 1 }

MGuardFirewallOutgoingLanDmzEntry ::= SEQUENCE {
  mGuardFWLDOUTruleIndex                   INTEGER,
  mGuardFWLDOUTproto                       INTEGER,
  mGuardFWLDOUTlog                         INTEGER,
  mGuardFWLDOUTRowStatus                   RowStatus,
  mGuardFWLDOUTcomment                     DisplayString,
  mGuardFWLDOUTfromMAC                     MacAddress,
  mGuardFWLDOUTtargetOrRuleValue           INTEGER,
  mGuardFWLDOUTtargetOrRuleRef             OBJECT IDENTIFIER,
  mGuardFWLDOUTsourceIPOrGroupValue        DisplayString,
  mGuardFWLDOUTsourceIPOrGroupRef          OBJECT IDENTIFIER,
  mGuardFWLDOUTdestinationIPOrGroupValue   DisplayString,
  mGuardFWLDOUTdestinationIPOrGroupRef     OBJECT IDENTIFIER,
  mGuardFWLDOUTsportOrGroupValue           DisplayString,
  mGuardFWLDOUTsportOrGroupRef             OBJECT IDENTIFIER,
  mGuardFWLDOUTdportOrGroupValue           DisplayString,
  mGuardFWLDOUTdportOrGroupRef             OBJECT IDENTIFIER
}

-- FW_OUTGOING_LANDMZ table index
mGuardFWLDOUTruleIndex OBJECT-TYPE
  SYNTAX INTEGER (1..2147483647)
  ACCESS not-accessible
  STATUS mandatory
  DESCRIPTION
    "Index to FW_OUTGOING_LANDMZ"
  ::= { mGuardFirewallOutgoingLanDmzEntry 1 }

-- FW_OUTGOING_LANDMZ row status
mGuardFWLDOUTRowStatus OBJECT-TYPE
  SYNTAX RowStatus
  ACCESS read-write
  STATUS mandatory
  DESCRIPTION
    "RowStatus of FW_OUTGOING_LANDMZ"
  ::= { mGuardFirewallOutgoingLanDmzEntry 9 }

-- FW_OUTGOING_LANDMZ.COMMENT
mGuardFWLDOUTcomment OBJECT-TYPE
  SYNTAX DisplayString
  ACCESS read-write
  STATUS mandatory
  DESCRIPTION
    "Variable name: FW_OUTGOING_LANDMZ.COMMENT
    WebUi Label: Comment
    Commentary or name for this rule."
  ::= { mGuardFirewallOutgoingLanDmzEntry 10 }

-- FW_OUTGOING_LANDMZ.FROM_PORT
mGuardFWLDOUTsportOrGroupValue OBJECT-TYPE
  SYNTAX DisplayString
  ACCESS read-write
  STATUS mandatory
  DESCRIPTION
    "Variable name: FW_OUTGOING_LANDMZ.FROM_PORT
    WebUi Label: From port
    The rule's source port"
  ::= { mGuardFirewallOutgoingLanDmzEntry 20 }

-- FW_OUTGOING_LANDMZ.FROM_PORT reference
mGuardFWLDOUTsportOrGroupRef OBJECT-TYPE
  SYNTAX OBJECT IDENTIFIER
  ACCESS read-write
  STATUS mandatory
  DESCRIPTION
    "Variable name: FW_OUTGOING_LANDMZ.FROM_PORT
    WebUi Label: From port
    The rule's source port as reference to port group"
  ::= { mGuardFirewallOutgoingLanDmzEntry 21 }

-- FW_OUTGOING_LANDMZ.LOG
mGuardFWLDOUTlog OBJECT-TYPE
  SYNTAX INTEGER {
    yes(1),
    no(2)
  }
  ACCESS read-write
  STATUS mandatory
  DESCRIPTION
    "Variable name: FW_OUTGOING_LANDMZ.LOG
    WebUi Label: Log
    Log packets matching this rule ?"
  ::= { mGuardFirewallOutgoingLanDmzEntry 8 }

-- FW_OUTGOING_LANDMZ.PROTO
mGuardFWLDOUTproto OBJECT-TYPE
  SYNTAX INTEGER {
    tcp(1),
    udp(2),
    icmp(3),
    all(4),
    gre(5)
  }
  ACCESS read-write
  STATUS mandatory
  DESCRIPTION
    "Variable name: FW_OUTGOING_LANDMZ.PROTO
    WebUi Label: Protocol
    The rule's transport protocol"
  ::= { mGuardFirewallOutgoingLanDmzEntry 7 }

-- FW_OUTGOING_LANDMZ.FROM_IP
mGuardFWLDOUTsourceIPOrGroupValue OBJECT-TYPE
  SYNTAX DisplayString
  ACCESS read-write
  STATUS mandatory
  DESCRIPTION
    "Variable name: FW_OUTGOING_LANDMZ.FROM_IP
    WebUi Label: From IP
    The rule's source IP address"
  ::= { mGuardFirewallOutgoingLanDmzEntry 16 }

-- FW_OUTGOING_LANDMZ.FROM_IP reference
mGuardFWLDOUTsourceIPOrGroupRef OBJECT-TYPE
  SYNTAX OBJECT IDENTIFIER
  ACCESS read-write
  STATUS mandatory
  DESCRIPTION
    "Variable name: FW_OUTGOING_LANDMZ.FROM_IP
    WebUi Label: From IP
    The rule's source IP address as reference to IP group"
  ::= { mGuardFirewallOutgoingLanDmzEntry 17 }

-- FW_OUTGOING_LANDMZ.IN_IP
mGuardFWLDOUTdestinationIPOrGroupValue OBJECT-TYPE
  SYNTAX DisplayString
  ACCESS read-write
  STATUS mandatory
  DESCRIPTION
    "Variable name: FW_OUTGOING_LANDMZ.IN_IP
    WebUi Label: To IP
    The rule's destination IP address"
  ::= { mGuardFirewallOutgoingLanDmzEntry 18 }

-- FW_OUTGOING_LANDMZ.IN_IP reference
mGuardFWLDOUTdestinationIPOrGroupRef OBJECT-TYPE
  SYNTAX OBJECT IDENTIFIER
  ACCESS read-write
  STATUS mandatory
  DESCRIPTION
    "Variable name: FW_OUTGOING_LANDMZ.IN_IP
    WebUi Label: To IP
    The rule's destination IP address as reference to IP group"
  ::= { mGuardFirewallOutgoingLanDmzEntry 19 }

-- FW_OUTGOING_LANDMZ.TARGET_REF
mGuardFWLDOUTtargetOrRuleValue OBJECT-TYPE
  SYNTAX INTEGER {
    accept(1),
    reject(2),
    drop(3)
  }
  ACCESS read-write
  STATUS mandatory
  DESCRIPTION
    "Variable name: FW_OUTGOING_LANDMZ.TARGET_REF
    WebUi Label: Action
    This object is effective if and only if the
    'mGuardFWLDOUTtargetOrRuleRef' object contains the OID of this object.
    When this object is read, it always returns the one of the values
    'accept', 'reject' or 'drop' . When one of the values is written to
    this object, no firewall rule set is used."
  ::= { mGuardFirewallOutgoingLanDmzEntry 14 }

-- FW_OUTGOING_LANDMZ.TARGET_REF reference
mGuardFWLDOUTtargetOrRuleRef OBJECT-TYPE
  SYNTAX OBJECT IDENTIFIER
  ACCESS read-write
  STATUS mandatory
  DESCRIPTION
    "Variable name: FW_OUTGOING_LANDMZ.TARGET_REF
    WebUi Label: Action
    When this object contains the OID of an 'mGuardFWRuleIndex' object,
    the corresponding firewall rule record is used for this firewall rule.
    To select a firewall rule record in this manner, write the OID of the
    corresponding 'mGuardFWRuleIndex' object to this object. To disable
    this feature, set the 'mGuardFWLDOUTtargetOrRuleValue' object."
  ::= { mGuardFirewallOutgoingLanDmzEntry 15 }

-- FW_OUTGOING_LANDMZ.FROM_MAC
mGuardFWLDOUTfromMAC OBJECT-TYPE
  SYNTAX MacAddress
  ACCESS read-write
  STATUS mandatory
  DESCRIPTION
    "Variable name: FW_OUTGOING_LANDMZ.FROM_MAC
    WebUi Label: From MAC
    The rule's source MAC address."
  ::= { mGuardFirewallOutgoingLanDmzEntry 11 }

-- FW_OUTGOING_LANDMZ.IN_PORT
mGuardFWLDOUTdportOrGroupValue OBJECT-TYPE
  SYNTAX DisplayString
  ACCESS read-write
  STATUS mandatory
  DESCRIPTION
    "Variable name: FW_OUTGOING_LANDMZ.IN_PORT
    WebUi Label: To port
    The rule's destination port"
  ::= { mGuardFirewallOutgoingLanDmzEntry 22 }

-- FW_OUTGOING_LANDMZ.IN_PORT reference
mGuardFWLDOUTdportOrGroupRef OBJECT-TYPE
  SYNTAX OBJECT IDENTIFIER
  ACCESS read-write
  STATUS mandatory
  DESCRIPTION
    "Variable name: FW_OUTGOING_LANDMZ.IN_PORT
    WebUi Label: To port
    The rule's destination port as reference to port group"
  ::= { mGuardFirewallOutgoingLanDmzEntry 23 }

-- FW_PORTFORWARDING
mGuardFirewallFWDuuid OBJECT-TYPE
  SYNTAX DisplayString
  ACCESS read-only
  STATUS mandatory
  DESCRIPTION
    "Variable name: FW_PORTFORWARDING
    WebUi Label: IP and port forwarding
    Universally Unique Identifier (UUID, RFC 4122) used for
    mGuardFirewallPortforwardTable logging."
  ::= { mGuardFirewallPortforwarding 2 }


-- FW_PORTFORWARDING table
mGuardFirewallPortforwardTable OBJECT-TYPE
  SYNTAX SEQUENCE OF MGuardFirewallPortforwardEntry
  ACCESS not-accessible
  STATUS mandatory
  DESCRIPTION
    "A table of FW_PORTFORWARDING"
  ::= { mGuardFirewallPortforwarding 1 }

-- FW_PORTFORWARDING table entry
mGuardFirewallPortforwardEntry OBJECT-TYPE
  SYNTAX MGuardFirewallPortforwardEntry
  ACCESS not-accessible
  STATUS mandatory
  DESCRIPTION
    "An entry of FW_PORTFORWARDING"
  INDEX { mGuardFWPORTFORWruleIndex }
  ::= { mGuardFirewallPortforwardTable 1 }

MGuardFirewallPortforwardEntry ::= SEQUENCE {
  mGuardFWPORTFORWruleIndex                INTEGER,
  mGuardFWPORTFORWinIP                     DisplayString,
  mGuardFWPORTFORWoutIP                    DisplayString,
  mGuardFWPORTFORWinport                   DisplayString,
  mGuardFWPORTFORWoutport                  DisplayString,
  mGuardFWPORTFORWproto                    INTEGER,
  mGuardFWPORTFORWlog                      INTEGER,
  mGuardFWPORTFORWRowStatus                RowStatus,
  mGuardFWPORTFORWcomment                  DisplayString,
  mGuardFWPORTFORWsrcMAC                   MacAddress,
  mGuardFWPORTFORWtarget                   INTEGER,
  mGuardFWPORTFORWsrcIPOrGroupValue        DisplayString,
  mGuardFWPORTFORWsrcIPOrGroupRef          OBJECT IDENTIFIER,
  mGuardFWPORTFORWsrcportOrGroupValue      DisplayString,
  mGuardFWPORTFORWsrcportOrGroupRef        OBJECT IDENTIFIER
}

-- FW_PORTFORWARDING table index
mGuardFWPORTFORWruleIndex OBJECT-TYPE
  SYNTAX INTEGER (1..2147483647)
  ACCESS not-accessible
  STATUS mandatory
  DESCRIPTION
    "Index to FW_PORTFORWARDING"
  ::= { mGuardFirewallPortforwardEntry 1 }

-- FW_PORTFORWARDING row status
mGuardFWPORTFORWRowStatus OBJECT-TYPE
  SYNTAX RowStatus
  ACCESS read-write
  STATUS mandatory
  DESCRIPTION
    "RowStatus of FW_PORTFORWARDING"
  ::= { mGuardFirewallPortforwardEntry 8 }

-- FW_PORTFORWARDING.COMMENT
mGuardFWPORTFORWcomment OBJECT-TYPE
  SYNTAX DisplayString
  ACCESS read-write
  STATUS mandatory
  DESCRIPTION
    "Variable name: FW_PORTFORWARDING.COMMENT
    WebUi Label: Comment
    Commentary or name for this rule."
  ::= { mGuardFirewallPortforwardEntry 11 }

-- FW_PORTFORWARDING.SRC_PORT
mGuardFWPORTFORWsrcportOrGroupValue OBJECT-TYPE
  SYNTAX DisplayString
  ACCESS read-write
  STATUS mandatory
  DESCRIPTION
    "Variable name: FW_PORTFORWARDING.SRC_PORT
    WebUi Label: From port
    The rule's source port"
  ::= { mGuardFirewallPortforwardEntry 20 }

-- FW_PORTFORWARDING.SRC_PORT reference
mGuardFWPORTFORWsrcportOrGroupRef OBJECT-TYPE
  SYNTAX OBJECT IDENTIFIER
  ACCESS read-write
  STATUS mandatory
  DESCRIPTION
    "Variable name: FW_PORTFORWARDING.SRC_PORT
    WebUi Label: From port
    The rule's source port as reference to port group"
  ::= { mGuardFirewallPortforwardEntry 21 }

-- FW_PORTFORWARDING.LOG
mGuardFWPORTFORWlog OBJECT-TYPE
  SYNTAX INTEGER {
    yes(1),
    no(2)
  }
  ACCESS read-write
  STATUS mandatory
  DESCRIPTION
    "Variable name: FW_PORTFORWARDING.LOG
    WebUi Label: Log
    Log packets matching this rule ?"
  ::= { mGuardFirewallPortforwardEntry 7 }

-- FW_PORTFORWARDING.PROTO
mGuardFWPORTFORWproto OBJECT-TYPE
  SYNTAX INTEGER {
    tcp(1),
    udp(2),
    gre(3)
  }
  ACCESS read-write
  STATUS mandatory
  DESCRIPTION
    "Variable name: FW_PORTFORWARDING.PROTO
    WebUi Label: Protocol
    The rule's transport protocol"
  ::= { mGuardFirewallPortforwardEntry 6 }

-- FW_PORTFORWARDING.OUT_IP
mGuardFWPORTFORWoutIP OBJECT-TYPE
  SYNTAX DisplayString
  ACCESS read-write
  STATUS mandatory
  DESCRIPTION
    "Variable name: FW_PORTFORWARDING.OUT_IP
    WebUi Label: Redirect to IP
    The rule's redirect IP address"
  ::= { mGuardFirewallPortforwardEntry 3 }

-- FW_PORTFORWARDING.IN_IP
mGuardFWPORTFORWinIP OBJECT-TYPE
  SYNTAX DisplayString
  ACCESS read-write
  STATUS mandatory
  DESCRIPTION
    "Variable name: FW_PORTFORWARDING.IN_IP
    WebUi Label: Incoming on IP
    The rule's incoming IP address"
  ::= { mGuardFirewallPortforwardEntry 2 }

-- FW_PORTFORWARDING.SRC_IP
mGuardFWPORTFORWsrcIPOrGroupValue OBJECT-TYPE
  SYNTAX DisplayString
  ACCESS read-write
  STATUS mandatory
  DESCRIPTION
    "Variable name: FW_PORTFORWARDING.SRC_IP
    WebUi Label: From IP
    The rule's source IP address"
  ::= { mGuardFirewallPortforwardEntry 16 }

-- FW_PORTFORWARDING.SRC_IP reference
mGuardFWPORTFORWsrcIPOrGroupRef OBJECT-TYPE
  SYNTAX OBJECT IDENTIFIER
  ACCESS read-write
  STATUS mandatory
  DESCRIPTION
    "Variable name: FW_PORTFORWARDING.SRC_IP
    WebUi Label: From IP
    The rule's source IP address as reference to IP group"
  ::= { mGuardFirewallPortforwardEntry 17 }

-- FW_PORTFORWARDING.OUT_PORT
mGuardFWPORTFORWoutport OBJECT-TYPE
  SYNTAX DisplayString
  ACCESS read-write
  STATUS mandatory
  DESCRIPTION
    "Variable name: FW_PORTFORWARDING.OUT_PORT
    WebUi Label: Redirect to port
    The rule's destination port"
  ::= { mGuardFirewallPortforwardEntry 5 }

-- FW_PORTFORWARDING.SRC_MAC
mGuardFWPORTFORWsrcMAC OBJECT-TYPE
  SYNTAX MacAddress
  ACCESS read-write
  STATUS mandatory
  DESCRIPTION
    "Variable name: FW_PORTFORWARDING.SRC_MAC
    WebUi Label: From MAC
    Commentary or name for this rule."
  ::= { mGuardFirewallPortforwardEntry 12 }

-- FW_PORTFORWARDING.IN_PORT
mGuardFWPORTFORWinport OBJECT-TYPE
  SYNTAX DisplayString
  ACCESS read-write
  STATUS mandatory
  DESCRIPTION
    "Variable name: FW_PORTFORWARDING.IN_PORT
    WebUi Label: Incoming on port
    The rule's incoming port"
  ::= { mGuardFirewallPortforwardEntry 4 }

-- FW_PORTFORWARDING.TARGET
mGuardFWPORTFORWtarget OBJECT-TYPE
  SYNTAX INTEGER {
    accept(1),
    reject(2),
    drop(3)
  }
  ACCESS read-write
  STATUS mandatory
  DESCRIPTION
    "Variable name: FW_PORTFORWARDING.TARGET
    WebUi Label: Action
    The target of the rule (accept/reject/drop)."
  ::= { mGuardFirewallPortforwardEntry 13 }


-- FW_RULESETS table
mGuardFirewallRuleTable OBJECT-TYPE
  SYNTAX SEQUENCE OF MGuardFirewallRuleEntry
  ACCESS not-accessible
  STATUS mandatory
  DESCRIPTION
    "A table of FW_RULESETS"
  ::= { mGuardFirewallRules 1 }

-- FW_RULESETS table entry
mGuardFirewallRuleEntry OBJECT-TYPE
  SYNTAX MGuardFirewallRuleEntry
  ACCESS not-accessible
  STATUS mandatory
  DESCRIPTION
    "An entry of FW_RULESETS"
  INDEX { mGuardFWRuleIndex }
  ::= { mGuardFirewallRuleTable 1 }

MGuardFirewallRuleEntry ::= SEQUENCE {
  mGuardFWRuleIndex                        INTEGER,
  mGuardFWRuleName                         DisplayString,
  mGuardFWRuleUuid                         DisplayString,
  mGuardFWRuleTimeout                      INTEGER,
  mGuardFWRuleActive                       INTEGER,
  mGuardFWRuleControlValue                 DisplayString,
  mGuardFWRuleControlRef                   OBJECT IDENTIFIER,
  mGuardFWRuleControlInv                   INTEGER,
  mGuardFWRuleSmsToken                     DisplayString,
  mGuardFWRuleRowStatus                    RowStatus
}

-- FW_RULESETS table index
mGuardFWRuleIndex OBJECT-TYPE
  SYNTAX INTEGER (1..2147483647)
  ACCESS not-accessible
  STATUS mandatory
  DESCRIPTION
    "Index to FW_RULESETS"
  ::= { mGuardFirewallRuleEntry 1 }

-- FW_RULESETS row status
mGuardFWRuleRowStatus OBJECT-TYPE
  SYNTAX RowStatus
  ACCESS read-write
  STATUS mandatory
  DESCRIPTION
    "RowStatus of FW_RULESETS"
  ::= { mGuardFirewallRuleEntry 20 }

-- FW_RULESETS.CONTROL
mGuardFWRuleControlValue OBJECT-TYPE
  SYNTAX DisplayString
  ACCESS read-write
  STATUS mandatory
  DESCRIPTION
    "Variable name: FW_RULESETS.CONTROL
    WebUi Label: Controlling service input or VPN connection
    This object is valid only if the object 'mGuardFWRuleControlRef'
    contains the OID of this object. Write 'cmd1', 'cmd2' or 'cmd3' to
    this object to control this rule with a command switch. Write 'none'
    to disable this feature. To control this rule by a VPN connection,
    write the 'mGuardFWRuleControlRef' object."
  ::= { mGuardFirewallRuleEntry 7 }

-- FW_RULESETS.CONTROL reference
mGuardFWRuleControlRef OBJECT-TYPE
  SYNTAX OBJECT IDENTIFIER
  ACCESS read-write
  STATUS mandatory
  DESCRIPTION
    "Variable name: FW_RULESETS.CONTROL
    WebUi Label: Controlling service input or VPN connection
    Configures the activation output. Write the OID of a
    'mGuardVPNconIndex' or 'mGuardOpenVPNConnectionIndex' to this object
    to control this rule by a VPN connection. Write the OID of the
    'mGuardFWRuleControlValue' object to this object to control this
    ruleset by a command switch or to disable this feature."
  ::= { mGuardFirewallRuleEntry 8 }

-- FW_RULESETS.SET
mGuardFWRuleUuid OBJECT-TYPE
  SYNTAX DisplayString
  ACCESS read-only
  STATUS mandatory
  DESCRIPTION
    "Variable name: FW_RULESETS.SET
    WebUi Label: Firewall Rules
    Universally Unique Identifier (UUID, RFC 4122) used for
    mGuardFirewallRuleSetTable logging."
  ::= { mGuardFirewallRuleEntry 4 }


-- FW_RULESETS.SET table
mGuardFWRuleSetTable OBJECT-TYPE
  SYNTAX SEQUENCE OF MGuardFWRuleSetEntry
  ACCESS not-accessible
  STATUS mandatory
  DESCRIPTION
    "A table of FW_RULESETS.SET"
  ::= { mGuardFirewallRules 2 }

-- FW_RULESETS.SET table entry
mGuardFWRuleSetEntry OBJECT-TYPE
  SYNTAX MGuardFWRuleSetEntry
  ACCESS not-accessible
  STATUS mandatory
  DESCRIPTION
    "An entry of FW_RULESETS.SET"
  INDEX { mGuardFWRuleIndex, mGuardFWRuleSetSetIndex }
  ::= { mGuardFWRuleSetTable 1 }

MGuardFWRuleSetEntry ::= SEQUENCE {
  mGuardFWRuleSetSetIndex                  INTEGER,
  mGuardFWRuleSetProto                     INTEGER,
  mGuardFWRuleSetLog                       INTEGER,
  mGuardFWRuleSetComment                   DisplayString,
  mGuardFWRuleSetSourceMAC                 MacAddress,
  mGuardFWRuleSetSourceIPOrGroupValue      DisplayString,
  mGuardFWRuleSetSourceIPOrGroupRef        OBJECT IDENTIFIER,
  mGuardFWRuleSetDestinationIPOrGroupValue DisplayString,
  mGuardFWRuleSetDestinationIPOrGroupRef   OBJECT IDENTIFIER,
  mGuardFWRuleSetSportOrGroupValue         DisplayString,
  mGuardFWRuleSetSportOrGroupRef           OBJECT IDENTIFIER,
  mGuardFWRuleSetDportOrGroupValue         DisplayString,
  mGuardFWRuleSetDportOrGroupRef           OBJECT IDENTIFIER,
  mGuardFWRuleSetRowStatus                 RowStatus,
  mGuardFWRuleSetTargetOrRuleValue         INTEGER,
  mGuardFWRuleSetTargetOrRuleRef           OBJECT IDENTIFIER
}

-- FW_RULESETS.SET table index
mGuardFWRuleSetSetIndex OBJECT-TYPE
  SYNTAX INTEGER (1..2147483647)
  ACCESS not-accessible
  STATUS mandatory
  DESCRIPTION
    "Index to FW_RULESETS.SET"
  ::= { mGuardFWRuleSetEntry 2 }

-- FW_RULESETS.SET row status
mGuardFWRuleSetRowStatus OBJECT-TYPE
  SYNTAX RowStatus
  ACCESS read-write
  STATUS mandatory
  DESCRIPTION
    "RowStatus of FW_RULESETS.SET"
  ::= { mGuardFWRuleSetEntry 50 }

-- FW_RULESETS.SET.COMMENT
mGuardFWRuleSetComment OBJECT-TYPE
  SYNTAX DisplayString
  ACCESS read-write
  STATUS mandatory
  DESCRIPTION
    "Variable name: FW_RULESETS.SET.COMMENT
    WebUi Label: Comment
    Commentary or name for this rule."
  ::= { mGuardFWRuleSetEntry 10 }

-- FW_RULESETS.SET.FROM_PORT
mGuardFWRuleSetSportOrGroupValue OBJECT-TYPE
  SYNTAX DisplayString
  ACCESS read-write
  STATUS mandatory
  DESCRIPTION
    "Variable name: FW_RULESETS.SET.FROM_PORT
    WebUi Label: From port
    The rule's source port"
  ::= { mGuardFWRuleSetEntry 20 }

-- FW_RULESETS.SET.FROM_PORT reference
mGuardFWRuleSetSportOrGroupRef OBJECT-TYPE
  SYNTAX OBJECT IDENTIFIER
  ACCESS read-write
  STATUS mandatory
  DESCRIPTION
    "Variable name: FW_RULESETS.SET.FROM_PORT
    WebUi Label: From port
    The rule's source port as reference to port group"
  ::= { mGuardFWRuleSetEntry 21 }

-- FW_RULESETS.SET.LOG
mGuardFWRuleSetLog OBJECT-TYPE
  SYNTAX INTEGER {
    yes(1),
    no(2)
  }
  ACCESS read-write
  STATUS mandatory
  DESCRIPTION
    "Variable name: FW_RULESETS.SET.LOG
    WebUi Label: Log
    Log packets matching this rule?"
  ::= { mGuardFWRuleSetEntry 9 }

-- FW_RULESETS.SET.PROTO
mGuardFWRuleSetProto OBJECT-TYPE
  SYNTAX INTEGER {
    icmp(1),
    tcp(6),
    udp(17),
    gre(47),
    all(256)
  }
  ACCESS read-write
  STATUS mandatory
  DESCRIPTION
    "Variable name: FW_RULESETS.SET.PROTO
    WebUi Label: Protocol
    The rule's transport protocol"
  ::= { mGuardFWRuleSetEntry 8 }

-- FW_RULESETS.SET.FROM_IP
mGuardFWRuleSetSourceIPOrGroupValue OBJECT-TYPE
  SYNTAX DisplayString
  ACCESS read-write
  STATUS mandatory
  DESCRIPTION
    "Variable name: FW_RULESETS.SET.FROM_IP
    WebUi Label: From IP
    The rule's source IP address"
  ::= { mGuardFWRuleSetEntry 16 }

-- FW_RULESETS.SET.FROM_IP reference
mGuardFWRuleSetSourceIPOrGroupRef OBJECT-TYPE
  SYNTAX OBJECT IDENTIFIER
  ACCESS read-write
  STATUS mandatory
  DESCRIPTION
    "Variable name: FW_RULESETS.SET.FROM_IP
    WebUi Label: From IP
    The rule's source IP address as reference to IP group"
  ::= { mGuardFWRuleSetEntry 17 }

-- FW_RULESETS.SET.IN_IP
mGuardFWRuleSetDestinationIPOrGroupValue OBJECT-TYPE
  SYNTAX DisplayString
  ACCESS read-write
  STATUS mandatory
  DESCRIPTION
    "Variable name: FW_RULESETS.SET.IN_IP
    WebUi Label: To IP
    The rule's destination IP address"
  ::= { mGuardFWRuleSetEntry 18 }

-- FW_RULESETS.SET.IN_IP reference
mGuardFWRuleSetDestinationIPOrGroupRef OBJECT-TYPE
  SYNTAX OBJECT IDENTIFIER
  ACCESS read-write
  STATUS mandatory
  DESCRIPTION
    "Variable name: FW_RULESETS.SET.IN_IP
    WebUi Label: To IP
    The rule's destination IP address as reference to IP group"
  ::= { mGuardFWRuleSetEntry 19 }

-- FW_RULESETS.SET.TARGET_REF
mGuardFWRuleSetTargetOrRuleValue OBJECT-TYPE
  SYNTAX INTEGER {
    accept(1),
    reject(2),
    drop(3)
  }
  ACCESS read-write
  STATUS mandatory
  DESCRIPTION
    "Variable name: FW_RULESETS.SET.TARGET_REF
    WebUi Label: Action
    This object is effective if and only if the
    'mGuardFWRuleSetTargetOrRuleRef' object contains the OID of this
    object. When this object is read, it always returns one of the values
    'accept', 'reject' or 'drop' . When one of the values is written to
    this object, no firewall rule set is used."
  ::= { mGuardFWRuleSetEntry 51 }

-- FW_RULESETS.SET.TARGET_REF reference
mGuardFWRuleSetTargetOrRuleRef OBJECT-TYPE
  SYNTAX OBJECT IDENTIFIER
  ACCESS read-write
  STATUS mandatory
  DESCRIPTION
    "Variable name: FW_RULESETS.SET.TARGET_REF
    WebUi Label: Action
    When this object contains the OID of an 'mGuardFWRuleIndex' object,
    the corresponding firewall rule record is used for this firewall rule.
    To select a firewall rule record in this manner, write the OID of the
    corresponding 'mGuardFWRuleIndex' object to this object. To disable
    this feature, set the 'mGuardFWRuleSetTargetOrRuleValue' object."
  ::= { mGuardFWRuleSetEntry 52 }

-- FW_RULESETS.SET.FROM_MAC
mGuardFWRuleSetSourceMAC OBJECT-TYPE
  SYNTAX MacAddress
  ACCESS read-write
  STATUS mandatory
  DESCRIPTION
    "Variable name: FW_RULESETS.SET.FROM_MAC
    WebUi Label: From MAC
    The rule's source MAC address."
  ::= { mGuardFWRuleSetEntry 11 }

-- FW_RULESETS.SET.IN_PORT
mGuardFWRuleSetDportOrGroupValue OBJECT-TYPE
  SYNTAX DisplayString
  ACCESS read-write
  STATUS mandatory
  DESCRIPTION
    "Variable name: FW_RULESETS.SET.IN_PORT
    WebUi Label: To port
    The rule's destination port"
  ::= { mGuardFWRuleSetEntry 22 }

-- FW_RULESETS.SET.IN_PORT reference
mGuardFWRuleSetDportOrGroupRef OBJECT-TYPE
  SYNTAX OBJECT IDENTIFIER
  ACCESS read-write
  STATUS mandatory
  DESCRIPTION
    "Variable name: FW_RULESETS.SET.IN_PORT
    WebUi Label: To port
    The rule's destination port as reference to port group"
  ::= { mGuardFWRuleSetEntry 23 }

-- FW_RULESETS.SET_ACTIVE
mGuardFWRuleActive OBJECT-TYPE
  SYNTAX INTEGER {
    disabled(1),
    inactive(2),
    active(3)
  }
  ACCESS read-write
  STATUS mandatory
  DESCRIPTION
    "Variable name: FW_RULESETS.SET_ACTIVE
    WebUi Label: Initial mode
    Controls the initial activation state of firewall rule sets."
  ::= { mGuardFirewallRuleEntry 6 }

-- FW_RULESETS.FRIENDLY_NAME
mGuardFWRuleName OBJECT-TYPE
  SYNTAX DisplayString
  ACCESS read-write
  STATUS mandatory
  DESCRIPTION
    "Variable name: FW_RULESETS.FRIENDLY_NAME
    WebUi Label: A descriptive name
    A name for the rule which will appear as target for
    mGuardFirewallIncoming and mGuardFirewallOutgoing. The name must not
    be one of 'ACCEPT', 'REJECT' or 'DROP'."
  ::= { mGuardFirewallRuleEntry 3 }

-- FW_RULESETS.TIMEOUT
mGuardFWRuleTimeout OBJECT-TYPE
  SYNTAX INTEGER(0..86400)
  ACCESS read-write
  STATUS mandatory
  DESCRIPTION
    "Variable name: FW_RULESETS.TIMEOUT
    WebUi Label: Deactivation timeout
    Timeout for temporarily activated rules."
  ::= { mGuardFirewallRuleEntry 5 }

-- FW_RULESETS.SMS_TOKEN
mGuardFWRuleSmsToken OBJECT-TYPE
  SYNTAX DisplayString
  ACCESS read-write
  STATUS mandatory
  DESCRIPTION
    "Variable name: FW_RULESETS.SMS_TOKEN
    WebUi Label: Token for text message trigger
    If set to any non-empty value, an incoming text message with this
    token will activate or deactivate the ruleset."
  ::= { mGuardFirewallRuleEntry 10 }

-- FW_RULESETS.CONTROL_INV
mGuardFWRuleControlInv OBJECT-TYPE
  SYNTAX INTEGER {
    yes(1),
    no(2)
  }
  ACCESS read-write
  STATUS mandatory
  DESCRIPTION
    "Variable name: FW_RULESETS.CONTROL_INV
    WebUi Label: Use inverted control logic
    Configures whether the activation input is low active."
  ::= { mGuardFirewallRuleEntry 9 }

-- GAI_PULL_DLTIME
mGuardProfilePullDownloadTimeout OBJECT-TYPE
  SYNTAX INTEGER(60..600)
  ACCESS read-write
  STATUS mandatory
  DESCRIPTION
    "Variable name: GAI_PULL_DLTIME
    WebUi Label: Download timeout
    Allowed download timeout to pull a remote configuration profile (in
    seconds)."
  ::= { mGuardProfilePull 7 }

-- GAI_PULL_HTTPS_CERT_REF
mGuardProfilePullHTTPSCertValue OBJECT-TYPE
  SYNTAX INTEGER {
    none(1)
  }
  ACCESS read-write
  STATUS mandatory
  DESCRIPTION
    "Variable name: GAI_PULL_HTTPS_CERT_REF
    WebUi Label: Server certificate
    X.509 Certificate of the HTTPS server to pull configuration profiles
    from. This used to authenticate the HTTPS server. This object is
    effective if and only if the 'mGuardProfilePullHTTPSCertRef' object
    contains the OID of this object. When this object is read, it always
    returns the value 'none'. When the value 'none' is written to this
    object, no Pull config server certificate is used."
  ::= { mGuardProfilePullHTTPS 10 }

-- GAI_PULL_HTTPS_CERT_REF reference
mGuardProfilePullHTTPSCertRef OBJECT-TYPE
  SYNTAX OBJECT IDENTIFIER
  ACCESS read-write
  STATUS mandatory
  DESCRIPTION
    "Variable name: GAI_PULL_HTTPS_CERT_REF
    WebUi Label: Server certificate
    When this object contains the OID of an 'mGuardCertsRemoteIndex'
    object, the corresponding remote certificate must match the pull
    config server certificate. When this object contains the OID of an
    'mGuardCertsCAIndex' object, the corresponding CA certificate is used
    to validate the pull config server."
  ::= { mGuardProfilePullHTTPS 11 }

-- GAI_PULL_HTTPS_DIR
mGuardProfilePullHTTPSDirectory OBJECT-TYPE
  SYNTAX DisplayString
  ACCESS read-write
  STATUS mandatory
  DESCRIPTION
    "Variable name: GAI_PULL_HTTPS_DIR
    WebUi Label: Directory
    Directory on the HTTPS server to pull configuration profiles from."
  ::= { mGuardProfilePullHTTPS 7 }

-- GAI_PULL_HTTPS_FILE
mGuardProfilePullHTTPSFile OBJECT-TYPE
  SYNTAX DisplayString
  ACCESS read-write
  STATUS mandatory
  DESCRIPTION
    "Variable name: GAI_PULL_HTTPS_FILE
    WebUi Label: Filename (If empty, the device serial number will be used.)
    Filename of the configuration to pull. Default is an empty name, in
    which case the serial number with the extension '.atv' is used."
  ::= { mGuardProfilePullHTTPS 4 }

-- GAI_PULL_HTTPS_HOST
mGuardProfilePullHTTPSServer OBJECT-TYPE
  SYNTAX DisplayString
  ACCESS read-write
  STATUS mandatory
  DESCRIPTION
    "Variable name: GAI_PULL_HTTPS_HOST
    WebUi Label: Server
    Hostname or IP of the HTTPS server to pull configuration profiles
    from."
  ::= { mGuardProfilePullHTTPS 2 }

-- GAI_PULL_HTTPS_LOGIN
mGuardProfilePullHTTPSLogin OBJECT-TYPE
  SYNTAX DisplayString
  ACCESS read-write
  STATUS mandatory
  DESCRIPTION
    "Variable name: GAI_PULL_HTTPS_LOGIN
    WebUi Label: Login
    Login on the HTTPS server to pull configuration profiles from."
  ::= { mGuardProfilePullHTTPS 5 }

-- GAI_PULL_HTTPS_PASSWORD
mGuardProfilePullHTTPSPasswd OBJECT-TYPE
  SYNTAX DisplayString
  ACCESS read-write
  STATUS mandatory
  DESCRIPTION
    "Variable name: GAI_PULL_HTTPS_PASSWORD
    WebUi Label: Password
    Password on the HTTPS server to pull configuration profiles from."
  ::= { mGuardProfilePullHTTPS 6 }

-- GAI_PULL_HTTPS_PORT
mGuardProfilePullHTTPSPort OBJECT-TYPE
  SYNTAX INTEGER(1..65535)
  ACCESS read-write
  STATUS mandatory
  DESCRIPTION
    "Variable name: GAI_PULL_HTTPS_PORT
    WebUi Label: Port
    Port of the HTTPS server to pull configuration profiles from. Usually
    443."
  ::= { mGuardProfilePullHTTPS 9 }

-- GAI_PULL_HTTPS_PREFER_VPN
mGuardProfilePullHTTPSPreferVPN OBJECT-TYPE
  SYNTAX INTEGER {
    yes(1),
    no(2)
  }
  ACCESS read-write
  STATUS mandatory
  DESCRIPTION
    "Variable name: GAI_PULL_HTTPS_PREFER_VPN
    WebUi Label: Via VPN
    Connect to HTTPS server via VPN if an applicable tunnel is configured.
    Important note: If set to 'yes', all proxy settings are ignored and no
    proxy will be used even if no applicable VPN tunnel exists! The HTTPS
    server will then be connected directly."
  ::= { mGuardProfilePullHTTPS 8 }

-- GAI_PULL_INTERVAL
mGuardProfilePullSchedule OBJECT-TYPE
  SYNTAX INTEGER {
    never(1),
    onboot(2),
    definitetime(3),
    quarterhourly(15),
    halfhourly(30),
    hourly(60),
    bihourly(120),
    sixhourly(360),
    twicedayly(720),
    dayly(1440)
  }
  ACCESS read-write
  STATUS mandatory
  DESCRIPTION
    "Variable name: GAI_PULL_INTERVAL
    WebUi Label: Pull schedule
    The period used when polling remote configuration profiles."
  ::= { mGuardProfilePull 1 }

-- GAI_PULL_ROLLBACK_BLOCK
mGuardProfilePullRollbackBlock OBJECT-TYPE
  SYNTAX INTEGER(0..100)
  ACCESS read-write
  STATUS mandatory
  DESCRIPTION
    "Variable name: GAI_PULL_ROLLBACK_BLOCK
    WebUi Label: Number of times a configuration profile is ignored after it was rolled
     back
    Number of denied configuration attempts after rollback."
  ::= { mGuardProfilePull 6 }

-- GAI_PULL_SCHEDULE
mGuardProfilePullScheduleDay OBJECT-TYPE
  SYNTAX INTEGER {
    monday(1),
    tuesday(2),
    wednesday(3),
    thursday(4),
    friday(5),
    saturday(6),
    sunday(7),
    everyday(8)
  }
  ACCESS read-write
  STATUS mandatory
  DESCRIPTION
    "Variable name: GAI_PULL_SCHEDULE
    WebUi Label: Time schedule
    Definite day."
  ::= { mGuardProfilePull 3 }

-- GAI_PULL_SCHEDULE_HOUR
mGuardProfilePullScheduleHour OBJECT-TYPE
  SYNTAX INTEGER(0..23)
  ACCESS read-write
  STATUS mandatory
  DESCRIPTION
    "Variable name: GAI_PULL_SCHEDULE_HOUR
    WebUi Label: Hours
    Definite hour."
  ::= { mGuardProfilePull 4 }

-- GAI_PULL_SCHEDULE_MIN
mGuardProfilePullScheduleMinute OBJECT-TYPE
  SYNTAX INTEGER(0..59)
  ACCESS read-write
  STATUS mandatory
  DESCRIPTION
    "Variable name: GAI_PULL_SCHEDULE_MIN
    WebUi Label: Minutes
    Definite minute."
  ::= { mGuardProfilePull 5 }

-- GPS_ENABLE
mGuardGpsEnable OBJECT-TYPE
  SYNTAX INTEGER {
    yes(1),
    no(2)
  }
  ACCESS read-write
  STATUS mandatory
  DESCRIPTION
    "Variable name: GPS_ENABLE
    WebUi Label: Enable positioning engine
    GPS Enable (yes, no)"
  ::= { mGuardGPS 1 }

-- GPS_UPDATE_CLOCK
mGuardGpsUpdateClock OBJECT-TYPE
  SYNTAX INTEGER {
    yes(1),
    no(2)
  }
  ACCESS read-write
  STATUS mandatory
  DESCRIPTION
    "Variable name: GPS_UPDATE_CLOCK
    WebUi Label: Update system time
    Use GPS time for system time update (yes, no)"
  ::= { mGuardGPS 2 }


-- GRE_TUNNEL table
mGuardGRETunnelTable OBJECT-TYPE
  SYNTAX SEQUENCE OF MGuardGRETunnelEntry
  ACCESS not-accessible
  STATUS mandatory
  DESCRIPTION
    "A table of GRE_TUNNEL"
  ::= { mGuardGRETunnel 1 }

-- GRE_TUNNEL table entry
mGuardGRETunnelEntry OBJECT-TYPE
  SYNTAX MGuardGRETunnelEntry
  ACCESS not-accessible
  STATUS mandatory
  DESCRIPTION
    "An entry of GRE_TUNNEL"
  INDEX { mGuardGRETunnelIndex }
  ::= { mGuardGRETunnelTable 1 }

MGuardGRETunnelEntry ::= SEQUENCE {
  mGuardGRETunnelIndex                     INTEGER,
  mGuardGRETunnelRowStatus                 RowStatus,
  mGuardGRETunnelSource                    IpAddress,
  mGuardGRETunnelDestination               IpAddress,
  mGuardGRETunnelVPNValue                  INTEGER,
  mGuardGRETunnelVPNRef                    OBJECT IDENTIFIER,
  mGuardGRETunnelIP                        IpAddress,
  mGuardGRETunnelMask                      IpAddress,
  mGuardGRETunnelOSPFAreaValue             INTEGER,
  mGuardGRETunnelOSPFAreaRef               OBJECT IDENTIFIER,
  mGuardGRETunnelOSPFMetric                INTEGER,
  mGuardGRETunnelFWLogDefIn                INTEGER,
  mGuardGRETunnelFWLogDefOut               INTEGER,
  mGuardGRETunnelFWInGlobal                INTEGER,
  mGuardGRETunnelFWOutGlobal               INTEGER
}

-- GRE_TUNNEL table index
mGuardGRETunnelIndex OBJECT-TYPE
  SYNTAX INTEGER (1..2147483647)
  ACCESS not-accessible
  STATUS mandatory
  DESCRIPTION
    "Index to GRE_TUNNEL"
  ::= { mGuardGRETunnelEntry 1 }

-- GRE_TUNNEL row status
mGuardGRETunnelRowStatus OBJECT-TYPE
  SYNTAX RowStatus
  ACCESS read-write
  STATUS mandatory
  DESCRIPTION
    "RowStatus of GRE_TUNNEL"
  ::= { mGuardGRETunnelEntry 2 }

-- GRE_TUNNEL.OSPF_METRIC
mGuardGRETunnelOSPFMetric OBJECT-TYPE
  SYNTAX INTEGER(1..65535)
  ACCESS read-write
  STATUS mandatory
  DESCRIPTION
    "Variable name: GRE_TUNNEL.OSPF_METRIC
    WebUi Label: OSPF metric
    Metric, used in OSPF for routing over the GRE tunnel."
  ::= { mGuardGRETunnelEntry 11 }

-- GRE_TUNNEL.VPN_CONNECTION_REF
mGuardGRETunnelVPNValue OBJECT-TYPE
  SYNTAX INTEGER {
    none(1)
  }
  ACCESS read-write
  STATUS mandatory
  DESCRIPTION
    "Variable name: GRE_TUNNEL.VPN_CONNECTION_REF
    WebUi Label: Use IPsec VPN connection for securing the tunnel
    This object is effective if and only if the 'mGuardGRETunnelVPNRef'
    object contains the OID of this object. When this object is read, it
    always returns the value 'none'. When the value 'none' is written to
    this object, no IPsec VPN connection will be bound to the GRE tunnel."
  ::= { mGuardGRETunnelEntry 5 }

-- GRE_TUNNEL.VPN_CONNECTION_REF reference
mGuardGRETunnelVPNRef OBJECT-TYPE
  SYNTAX OBJECT IDENTIFIER
  ACCESS read-write
  STATUS mandatory
  DESCRIPTION
    "Variable name: GRE_TUNNEL.VPN_CONNECTION_REF
    WebUi Label: Use IPsec VPN connection for securing the tunnel
    When this object contains the OID of a 'mGuardVPNconIndex' object,
    source and destination of this GRE tunnel are checked to reside inside
    the given IPsec VPN connection. To select a IPsec VPN connection in
    this manner, write the OID of the corresponding 'mGuardVPNconIndex'
    object to this object. To disable this feature, set the
    'mGuardGRETunnelVPNValue' object."
  ::= { mGuardGRETunnelEntry 6 }

-- GRE_TUNNEL.OSPF_AREA_REF
mGuardGRETunnelOSPFAreaValue OBJECT-TYPE
  SYNTAX INTEGER {
    none(1)
  }
  ACCESS read-write
  STATUS mandatory
  DESCRIPTION
    "Variable name: GRE_TUNNEL.OSPF_AREA_REF
    WebUi Label: OSPF area
    This object is effective if and only if the
    'mGuardGRETunnelOSPFAreaRef' object contains the OID of this object.
    When this object is read, it always returns the value 'none'. When the
    value 'none' is written to this object, no OSPF Area is used."
  ::= { mGuardGRETunnelEntry 9 }

-- GRE_TUNNEL.OSPF_AREA_REF reference
mGuardGRETunnelOSPFAreaRef OBJECT-TYPE
  SYNTAX OBJECT IDENTIFIER
  ACCESS read-write
  STATUS mandatory
  DESCRIPTION
    "Variable name: GRE_TUNNEL.OSPF_AREA_REF
    WebUi Label: OSPF area
    When this object contains the OID of an 'mGuardOSPFAreaIndex' object,
    the corresponding OSPF Area is attached to this GRE tunnel. To select
    an OSPF Area in this manner, write the OID of the corresponding
    'mGuardOSPFAreaIndex' object to this object. To disable this feature,
    set the 'mGuardGRETunnelOSPFAreaValue' object."
  ::= { mGuardGRETunnelEntry 10 }

-- GRE_TUNNEL.FW_OUTGOING_GLOBAL
mGuardGRETunnelFWOutGlobal OBJECT-TYPE
  SYNTAX INTEGER {
    accept(1),
    drop(2),
    rules(3),
    ping(4)
  }
  ACCESS read-write
  STATUS mandatory
  DESCRIPTION
    "Variable name: GRE_TUNNEL.FW_OUTGOING_GLOBAL
    WebUi Label: General firewall setting
    Global switch to accept or drop all outgoing connections or to follow
    the explicit firewall rules."
  ::= { mGuardGRETunnelEntry 16 }

-- GRE_TUNNEL.TUNNEL_SRC
mGuardGRETunnelSource OBJECT-TYPE
  SYNTAX IpAddress
  ACCESS read-write
  STATUS mandatory
  DESCRIPTION
    "Variable name: GRE_TUNNEL.TUNNEL_SRC
    WebUi Label: Local endpoint
    Local endpoint of the GRE tunnel. This IP address may be part of a
    local IPsec VPN network."
  ::= { mGuardGRETunnelEntry 3 }

-- GRE_TUNNEL.FW_OUTGOING
mGuardGRETunnelFWOUTuuid OBJECT-TYPE
  SYNTAX DisplayString
  ACCESS read-only
  STATUS mandatory
  DESCRIPTION
    "Variable name: GRE_TUNNEL.FW_OUTGOING
    WebUi Label: --
    Universally Unique Identifier (UUID, RFC 4122) used for
    mGuardGRETunnelFWOUTTable logging."
  ::= { mGuardGRETunnel 9 }


-- GRE_TUNNEL.FW_OUTGOING table
mGuardGRETunnelFWOUTTable OBJECT-TYPE
  SYNTAX SEQUENCE OF MGuardGRETunnelFWOUTEntry
  ACCESS not-accessible
  STATUS mandatory
  DESCRIPTION
    "A table of GRE_TUNNEL.FW_OUTGOING"
  ::= { mGuardGRETunnel 4 }

-- GRE_TUNNEL.FW_OUTGOING table entry
mGuardGRETunnelFWOUTEntry OBJECT-TYPE
  SYNTAX MGuardGRETunnelFWOUTEntry
  ACCESS not-accessible
  STATUS mandatory
  DESCRIPTION
    "An entry of GRE_TUNNEL.FW_OUTGOING"
  INDEX { mGuardGRETunnelIndex, mGuardGRETunnelFWOUTIndex }
  ::= { mGuardGRETunnelFWOUTTable 1 }

MGuardGRETunnelFWOUTEntry ::= SEQUENCE {
  mGuardGRETunnelFWOUTIndex                INTEGER,
  mGuardGRETunnelFWOUTRowStatus            RowStatus,
  mGuardGRETunnelFWOUTComment              DisplayString,
  mGuardGRETunnelFWOUTSourceIPOrGroupValue DisplayString,
  mGuardGRETunnelFWOUTSourceIPOrGroupRef   OBJECT IDENTIFIER,
  mGuardGRETunnelFWOUTDestinationIPOrGroupValue DisplayString,
  mGuardGRETunnelFWOUTDestinationIPOrGroupRef OBJECT IDENTIFIER,
  mGuardGRETunnelFWOUTSPortOrGroupValue    DisplayString,
  mGuardGRETunnelFWOUTSPortOrGroupRef      OBJECT IDENTIFIER,
  mGuardGRETunnelFWOUTDPortOrGroupValue    DisplayString,
  mGuardGRETunnelFWOUTDPortOrGroupRef      OBJECT IDENTIFIER,
  mGuardGRETunnelFWOUTLog                  INTEGER,
  mGuardGRETunnelFWOUTProto                INTEGER,
  mGuardGRETunnelFWOUTTargetValue          INTEGER,
  mGuardGRETunnelFWOUTTargetRef            OBJECT IDENTIFIER
}

-- GRE_TUNNEL.FW_OUTGOING table index
mGuardGRETunnelFWOUTIndex OBJECT-TYPE
  SYNTAX INTEGER (1..2147483647)
  ACCESS not-accessible
  STATUS mandatory
  DESCRIPTION
    "Index to GRE_TUNNEL.FW_OUTGOING"
  ::= { mGuardGRETunnelFWOUTEntry 1 }

-- GRE_TUNNEL.FW_OUTGOING row status
mGuardGRETunnelFWOUTRowStatus OBJECT-TYPE
  SYNTAX RowStatus
  ACCESS read-write
  STATUS mandatory
  DESCRIPTION
    "RowStatus of GRE_TUNNEL.FW_OUTGOING"
  ::= { mGuardGRETunnelFWOUTEntry 2 }

-- GRE_TUNNEL.FW_OUTGOING.COMMENT
mGuardGRETunnelFWOUTComment OBJECT-TYPE
  SYNTAX DisplayString
  ACCESS read-write
  STATUS mandatory
  DESCRIPTION
    "Variable name: GRE_TUNNEL.FW_OUTGOING.COMMENT
    WebUi Label: Comment
    Commentary or name for this rule."
  ::= { mGuardGRETunnelFWOUTEntry 4 }

-- GRE_TUNNEL.FW_OUTGOING.FROM_PORT
mGuardGRETunnelFWOUTSPortOrGroupValue OBJECT-TYPE
  SYNTAX DisplayString
  ACCESS read-write
  STATUS mandatory
  DESCRIPTION
    "Variable name: GRE_TUNNEL.FW_OUTGOING.FROM_PORT
    WebUi Label: From port
    The rule's source port"
  ::= { mGuardGRETunnelFWOUTEntry 9 }

-- GRE_TUNNEL.FW_OUTGOING.FROM_PORT reference
mGuardGRETunnelFWOUTSPortOrGroupRef OBJECT-TYPE
  SYNTAX OBJECT IDENTIFIER
  ACCESS read-write
  STATUS mandatory
  DESCRIPTION
    "Variable name: GRE_TUNNEL.FW_OUTGOING.FROM_PORT
    WebUi Label: From port
    The rule's source port as reference to port group"
  ::= { mGuardGRETunnelFWOUTEntry 10 }

-- GRE_TUNNEL.FW_OUTGOING.LOG
mGuardGRETunnelFWOUTLog OBJECT-TYPE
  SYNTAX INTEGER {
    yes(1),
    no(2)
  }
  ACCESS read-write
  STATUS mandatory
  DESCRIPTION
    "Variable name: GRE_TUNNEL.FW_OUTGOING.LOG
    WebUi Label: Log
    Log packets matching this rule."
  ::= { mGuardGRETunnelFWOUTEntry 13 }

-- GRE_TUNNEL.FW_OUTGOING.PROTO
mGuardGRETunnelFWOUTProto OBJECT-TYPE
  SYNTAX INTEGER {
    tcp(1),
    udp(2),
    icmp(3),
    all(4),
    gre(5)
  }
  ACCESS read-write
  STATUS mandatory
  DESCRIPTION
    "Variable name: GRE_TUNNEL.FW_OUTGOING.PROTO
    WebUi Label: Protocol
    The rule's transport protocol"
  ::= { mGuardGRETunnelFWOUTEntry 14 }

-- GRE_TUNNEL.FW_OUTGOING.FROM_IP
mGuardGRETunnelFWOUTSourceIPOrGroupValue OBJECT-TYPE
  SYNTAX DisplayString
  ACCESS read-write
  STATUS mandatory
  DESCRIPTION
    "Variable name: GRE_TUNNEL.FW_OUTGOING.FROM_IP
    WebUi Label: From IP
    The rule's source IP address"
  ::= { mGuardGRETunnelFWOUTEntry 5 }

-- GRE_TUNNEL.FW_OUTGOING.FROM_IP reference
mGuardGRETunnelFWOUTSourceIPOrGroupRef OBJECT-TYPE
  SYNTAX OBJECT IDENTIFIER
  ACCESS read-write
  STATUS mandatory
  DESCRIPTION
    "Variable name: GRE_TUNNEL.FW_OUTGOING.FROM_IP
    WebUi Label: From IP
    The rule's source IP address as reference to IP group"
  ::= { mGuardGRETunnelFWOUTEntry 6 }

-- GRE_TUNNEL.FW_OUTGOING.IN_IP
mGuardGRETunnelFWOUTDestinationIPOrGroupValue OBJECT-TYPE
  SYNTAX DisplayString
  ACCESS read-write
  STATUS mandatory
  DESCRIPTION
    "Variable name: GRE_TUNNEL.FW_OUTGOING.IN_IP
    WebUi Label: To IP
    The rule's destination IP address"
  ::= { mGuardGRETunnelFWOUTEntry 7 }

-- GRE_TUNNEL.FW_OUTGOING.IN_IP reference
mGuardGRETunnelFWOUTDestinationIPOrGroupRef OBJECT-TYPE
  SYNTAX OBJECT IDENTIFIER
  ACCESS read-write
  STATUS mandatory
  DESCRIPTION
    "Variable name: GRE_TUNNEL.FW_OUTGOING.IN_IP
    WebUi Label: To IP
    The rule's destination IP address as reference to IP group"
  ::= { mGuardGRETunnelFWOUTEntry 8 }

-- GRE_TUNNEL.FW_OUTGOING.TARGET_REF
mGuardGRETunnelFWOUTTargetValue OBJECT-TYPE
  SYNTAX INTEGER {
    accept(1),
    reject(2),
    drop(3)
  }
  ACCESS read-write
  STATUS mandatory
  DESCRIPTION
    "Variable name: GRE_TUNNEL.FW_OUTGOING.TARGET_REF
    WebUi Label: Action
    The rule's target. This object is effective if and only if the
    'mGuardGRETunnelFWOUTTargetRef' object contains the OID of this
    object."
  ::= { mGuardGRETunnelFWOUTEntry 15 }

-- GRE_TUNNEL.FW_OUTGOING.TARGET_REF reference
mGuardGRETunnelFWOUTTargetRef OBJECT-TYPE
  SYNTAX OBJECT IDENTIFIER
  ACCESS read-write
  STATUS mandatory
  DESCRIPTION
    "Variable name: GRE_TUNNEL.FW_OUTGOING.TARGET_REF
    WebUi Label: Action
    Set this object to the OID of an 'mGuardFWRuleIndex' to select a
    firewall ruleset as this rule's target. Set this object to the OID of
    the 'mGuardGRETunnelFWOUTTargetValue' object to choose a target from
    that objects range."
  ::= { mGuardGRETunnelFWOUTEntry 16 }

-- GRE_TUNNEL.FW_OUTGOING.IN_PORT
mGuardGRETunnelFWOUTDPortOrGroupValue OBJECT-TYPE
  SYNTAX DisplayString
  ACCESS read-write
  STATUS mandatory
  DESCRIPTION
    "Variable name: GRE_TUNNEL.FW_OUTGOING.IN_PORT
    WebUi Label: To port
    The rule's destination port"
  ::= { mGuardGRETunnelFWOUTEntry 11 }

-- GRE_TUNNEL.FW_OUTGOING.IN_PORT reference
mGuardGRETunnelFWOUTDPortOrGroupRef OBJECT-TYPE
  SYNTAX OBJECT IDENTIFIER
  ACCESS read-write
  STATUS mandatory
  DESCRIPTION
    "Variable name: GRE_TUNNEL.FW_OUTGOING.IN_PORT
    WebUi Label: To port
    The rule's destination port as reference to port group"
  ::= { mGuardGRETunnelFWOUTEntry 12 }

-- GRE_TUNNEL.INTERFACE_MASK
mGuardGRETunnelMask OBJECT-TYPE
  SYNTAX IpAddress
  ACCESS read-write
  STATUS mandatory
  DESCRIPTION
    "Variable name: GRE_TUNNEL.INTERFACE_MASK
    WebUi Label: Local interface mask (needed for OSPF routing)
    Mask of net residing inside the GRE tunnel."
  ::= { mGuardGRETunnelEntry 8 }

-- GRE_TUNNEL.LOG_DEFAULT_OUTGOING
mGuardGRETunnelFWLogDefOut OBJECT-TYPE
  SYNTAX INTEGER {
    yes(1),
    no(2)
  }
  ACCESS read-write
  STATUS mandatory
  DESCRIPTION
    "Variable name: GRE_TUNNEL.LOG_DEFAULT_OUTGOING
    WebUi Label: Log entries for unknown connection attempts
    Log entries for undefined outgoing connection attempts."
  ::= { mGuardGRETunnelEntry 14 }

-- GRE_TUNNEL.FW_INCOMING
mGuardGRETunnelFWINuuid OBJECT-TYPE
  SYNTAX DisplayString
  ACCESS read-only
  STATUS mandatory
  DESCRIPTION
    "Variable name: GRE_TUNNEL.FW_INCOMING
    WebUi Label: --
    Universally Unique Identifier (UUID, RFC 4122) used for
    mGuardGRETunnelFWINTable logging."
  ::= { mGuardGRETunnel 8 }


-- GRE_TUNNEL.FW_INCOMING table
mGuardGRETunnelFWINTable OBJECT-TYPE
  SYNTAX SEQUENCE OF MGuardGRETunnelFWINEntry
  ACCESS not-accessible
  STATUS mandatory
  DESCRIPTION
    "A table of GRE_TUNNEL.FW_INCOMING"
  ::= { mGuardGRETunnel 3 }

-- GRE_TUNNEL.FW_INCOMING table entry
mGuardGRETunnelFWINEntry OBJECT-TYPE
  SYNTAX MGuardGRETunnelFWINEntry
  ACCESS not-accessible
  STATUS mandatory
  DESCRIPTION
    "An entry of GRE_TUNNEL.FW_INCOMING"
  INDEX { mGuardGRETunnelIndex, mGuardGRETunnelFWINIndex }
  ::= { mGuardGRETunnelFWINTable 1 }

MGuardGRETunnelFWINEntry ::= SEQUENCE {
  mGuardGRETunnelFWINIndex                 INTEGER,
  mGuardGRETunnelFWINRowStatus             RowStatus,
  mGuardGRETunnelFWINComment               DisplayString,
  mGuardGRETunnelFWINSourceIPOrGroupValue  DisplayString,
  mGuardGRETunnelFWINSourceIPOrGroupRef    OBJECT IDENTIFIER,
  mGuardGRETunnelFWINDestinationIPOrGroupValue DisplayString,
  mGuardGRETunnelFWINDestinationIPOrGroupRef OBJECT IDENTIFIER,
  mGuardGRETunnelFWINSPortOrGroupValue     DisplayString,
  mGuardGRETunnelFWINSPortOrGroupRef       OBJECT IDENTIFIER,
  mGuardGRETunnelFWINDPortOrGroupValue     DisplayString,
  mGuardGRETunnelFWINDPortOrGroupRef       OBJECT IDENTIFIER,
  mGuardGRETunnelFWINLog                   INTEGER,
  mGuardGRETunnelFWINProto                 INTEGER,
  mGuardGRETunnelFWINTargetValue           INTEGER,
  mGuardGRETunnelFWINTargetRef             OBJECT IDENTIFIER
}

-- GRE_TUNNEL.FW_INCOMING table index
mGuardGRETunnelFWINIndex OBJECT-TYPE
  SYNTAX INTEGER (1..2147483647)
  ACCESS not-accessible
  STATUS mandatory
  DESCRIPTION
    "Index to GRE_TUNNEL.FW_INCOMING"
  ::= { mGuardGRETunnelFWINEntry 1 }

-- GRE_TUNNEL.FW_INCOMING row status
mGuardGRETunnelFWINRowStatus OBJECT-TYPE
  SYNTAX RowStatus
  ACCESS read-write
  STATUS mandatory
  DESCRIPTION
    "RowStatus of GRE_TUNNEL.FW_INCOMING"
  ::= { mGuardGRETunnelFWINEntry 2 }

-- GRE_TUNNEL.FW_INCOMING.COMMENT
mGuardGRETunnelFWINComment OBJECT-TYPE
  SYNTAX DisplayString
  ACCESS read-write
  STATUS mandatory
  DESCRIPTION
    "Variable name: GRE_TUNNEL.FW_INCOMING.COMMENT
    WebUi Label: Comment
    Commentary or name for this rule."
  ::= { mGuardGRETunnelFWINEntry 4 }

-- GRE_TUNNEL.FW_INCOMING.FROM_PORT
mGuardGRETunnelFWINSPortOrGroupValue OBJECT-TYPE
  SYNTAX DisplayString
  ACCESS read-write
  STATUS mandatory
  DESCRIPTION
    "Variable name: GRE_TUNNEL.FW_INCOMING.FROM_PORT
    WebUi Label: From port
    The rule's source port"
  ::= { mGuardGRETunnelFWINEntry 9 }

-- GRE_TUNNEL.FW_INCOMING.FROM_PORT reference
mGuardGRETunnelFWINSPortOrGroupRef OBJECT-TYPE
  SYNTAX OBJECT IDENTIFIER
  ACCESS read-write
  STATUS mandatory
  DESCRIPTION
    "Variable name: GRE_TUNNEL.FW_INCOMING.FROM_PORT
    WebUi Label: From port
    The rule's source port as reference to port group"
  ::= { mGuardGRETunnelFWINEntry 10 }

-- GRE_TUNNEL.FW_INCOMING.LOG
mGuardGRETunnelFWINLog OBJECT-TYPE
  SYNTAX INTEGER {
    yes(1),
    no(2)
  }
  ACCESS read-write
  STATUS mandatory
  DESCRIPTION
    "Variable name: GRE_TUNNEL.FW_INCOMING.LOG
    WebUi Label: Log
    Log packets matching this rule."
  ::= { mGuardGRETunnelFWINEntry 13 }

-- GRE_TUNNEL.FW_INCOMING.PROTO
mGuardGRETunnelFWINProto OBJECT-TYPE
  SYNTAX INTEGER {
    tcp(1),
    udp(2),
    icmp(3),
    all(4),
    gre(5)
  }
  ACCESS read-write
  STATUS mandatory
  DESCRIPTION
    "Variable name: GRE_TUNNEL.FW_INCOMING.PROTO
    WebUi Label: Protocol
    The rule's transport protocol"
  ::= { mGuardGRETunnelFWINEntry 14 }

-- GRE_TUNNEL.FW_INCOMING.FROM_IP
mGuardGRETunnelFWINSourceIPOrGroupValue OBJECT-TYPE
  SYNTAX DisplayString
  ACCESS read-write
  STATUS mandatory
  DESCRIPTION
    "Variable name: GRE_TUNNEL.FW_INCOMING.FROM_IP
    WebUi Label: From IP
    The rule's source IP address"
  ::= { mGuardGRETunnelFWINEntry 5 }

-- GRE_TUNNEL.FW_INCOMING.FROM_IP reference
mGuardGRETunnelFWINSourceIPOrGroupRef OBJECT-TYPE
  SYNTAX OBJECT IDENTIFIER
  ACCESS read-write
  STATUS mandatory
  DESCRIPTION
    "Variable name: GRE_TUNNEL.FW_INCOMING.FROM_IP
    WebUi Label: From IP
    The rule's source IP address as reference to IP group"
  ::= { mGuardGRETunnelFWINEntry 6 }

-- GRE_TUNNEL.FW_INCOMING.IN_IP
mGuardGRETunnelFWINDestinationIPOrGroupValue OBJECT-TYPE
  SYNTAX DisplayString
  ACCESS read-write
  STATUS mandatory
  DESCRIPTION
    "Variable name: GRE_TUNNEL.FW_INCOMING.IN_IP
    WebUi Label: To IP
    The rule's destination IP address"
  ::= { mGuardGRETunnelFWINEntry 7 }

-- GRE_TUNNEL.FW_INCOMING.IN_IP reference
mGuardGRETunnelFWINDestinationIPOrGroupRef OBJECT-TYPE
  SYNTAX OBJECT IDENTIFIER
  ACCESS read-write
  STATUS mandatory
  DESCRIPTION
    "Variable name: GRE_TUNNEL.FW_INCOMING.IN_IP
    WebUi Label: To IP
    The rule's destination IP address as reference to IP group"
  ::= { mGuardGRETunnelFWINEntry 8 }

-- GRE_TUNNEL.FW_INCOMING.TARGET_REF
mGuardGRETunnelFWINTargetValue OBJECT-TYPE
  SYNTAX INTEGER {
    accept(1),
    reject(2),
    drop(3)
  }
  ACCESS read-write
  STATUS mandatory
  DESCRIPTION
    "Variable name: GRE_TUNNEL.FW_INCOMING.TARGET_REF
    WebUi Label: Action
    The rule's target. This object is effective if and only if the
    'mGuardGRETunnelFWINTargetRef' object contains the OID of this object."
  ::= { mGuardGRETunnelFWINEntry 15 }

-- GRE_TUNNEL.FW_INCOMING.TARGET_REF reference
mGuardGRETunnelFWINTargetRef OBJECT-TYPE
  SYNTAX OBJECT IDENTIFIER
  ACCESS read-write
  STATUS mandatory
  DESCRIPTION
    "Variable name: GRE_TUNNEL.FW_INCOMING.TARGET_REF
    WebUi Label: Action
    Set this object to the OID of an 'mGuardFWRuleIndex' to select a
    firewall ruleset as this rule's target. Set this object to the OID of
    the 'mGuardGRETunnelFWINTargetValue' object to choose a target from
    that objects range."
  ::= { mGuardGRETunnelFWINEntry 16 }

-- GRE_TUNNEL.FW_INCOMING.IN_PORT
mGuardGRETunnelFWINDPortOrGroupValue OBJECT-TYPE
  SYNTAX DisplayString
  ACCESS read-write
  STATUS mandatory
  DESCRIPTION
    "Variable name: GRE_TUNNEL.FW_INCOMING.IN_PORT
    WebUi Label: To port
    The rule's destination port"
  ::= { mGuardGRETunnelFWINEntry 11 }

-- GRE_TUNNEL.FW_INCOMING.IN_PORT reference
mGuardGRETunnelFWINDPortOrGroupRef OBJECT-TYPE
  SYNTAX OBJECT IDENTIFIER
  ACCESS read-write
  STATUS mandatory
  DESCRIPTION
    "Variable name: GRE_TUNNEL.FW_INCOMING.IN_PORT
    WebUi Label: To port
    The rule's destination port as reference to port group"
  ::= { mGuardGRETunnelFWINEntry 12 }


-- GRE_TUNNEL.ROUTES table
mGuardGRETunnelRoutesTable OBJECT-TYPE
  SYNTAX SEQUENCE OF MGuardGRETunnelRoutesEntry
  ACCESS not-accessible
  STATUS mandatory
  DESCRIPTION
    "A table of GRE_TUNNEL.ROUTES"
  ::= { mGuardGRETunnel 2 }

-- GRE_TUNNEL.ROUTES table entry
mGuardGRETunnelRoutesEntry OBJECT-TYPE
  SYNTAX MGuardGRETunnelRoutesEntry
  ACCESS not-accessible
  STATUS mandatory
  DESCRIPTION
    "An entry of GRE_TUNNEL.ROUTES"
  INDEX { mGuardGRETunnelIndex, mGuardGRETunnelRoutesIndex }
  ::= { mGuardGRETunnelRoutesTable 1 }

MGuardGRETunnelRoutesEntry ::= SEQUENCE {
  mGuardGRETunnelRoutesIndex               INTEGER,
  mGuardGRETunnelRoutesRowStatus           RowStatus,
  mGuardGRETunnelRoutesNetwork             DisplayString
}

-- GRE_TUNNEL.ROUTES table index
mGuardGRETunnelRoutesIndex OBJECT-TYPE
  SYNTAX INTEGER (1..2147483647)
  ACCESS not-accessible
  STATUS mandatory
  DESCRIPTION
    "Index to GRE_TUNNEL.ROUTES"
  ::= { mGuardGRETunnelRoutesEntry 1 }

-- GRE_TUNNEL.ROUTES row status
mGuardGRETunnelRoutesRowStatus OBJECT-TYPE
  SYNTAX RowStatus
  ACCESS read-write
  STATUS mandatory
  DESCRIPTION
    "RowStatus of GRE_TUNNEL.ROUTES"
  ::= { mGuardGRETunnelRoutesEntry 2 }

-- GRE_TUNNEL.ROUTES.NETWORK
mGuardGRETunnelRoutesNetwork OBJECT-TYPE
  SYNTAX DisplayString
  ACCESS read-write
  STATUS mandatory
  DESCRIPTION
    "Variable name: GRE_TUNNEL.ROUTES.NETWORK
    WebUi Label: Network
    Network which should be routed over the GRE tunnel."
  ::= { mGuardGRETunnelRoutesEntry 3 }

-- GRE_TUNNEL.INTERFACE_IP
mGuardGRETunnelIP OBJECT-TYPE
  SYNTAX IpAddress
  ACCESS read-write
  STATUS mandatory
  DESCRIPTION
    "Variable name: GRE_TUNNEL.INTERFACE_IP
    WebUi Label: Local interface IP (needed for OSPF routing)
    Local IP inside the GRE tunnel. Used as next hop for routing."
  ::= { mGuardGRETunnelEntry 7 }

-- GRE_TUNNEL.FW_INCOMING_GLOBAL
mGuardGRETunnelFWInGlobal OBJECT-TYPE
  SYNTAX INTEGER {
    accept(1),
    drop(2),
    rules(3),
    ping(4)
  }
  ACCESS read-write
  STATUS mandatory
  DESCRIPTION
    "Variable name: GRE_TUNNEL.FW_INCOMING_GLOBAL
    WebUi Label: General firewall setting
    Global switch to accept or drop all incoming connections or to follow
    the explicit firewall rules."
  ::= { mGuardGRETunnelEntry 15 }

-- GRE_TUNNEL.TUNNEL_DST
mGuardGRETunnelDestination OBJECT-TYPE
  SYNTAX IpAddress
  ACCESS read-write
  STATUS mandatory
  DESCRIPTION
    "Variable name: GRE_TUNNEL.TUNNEL_DST
    WebUi Label: Remote endpoint
    Remote endpoint of the GRE tunnel. This IP address may be part of a
    remote IPsec VPN network."
  ::= { mGuardGRETunnelEntry 4 }

-- GRE_TUNNEL.LOG_DEFAULT_INCOMING
mGuardGRETunnelFWLogDefIn OBJECT-TYPE
  SYNTAX INTEGER {
    yes(1),
    no(2)
  }
  ACCESS read-write
  STATUS mandatory
  DESCRIPTION
    "Variable name: GRE_TUNNEL.LOG_DEFAULT_INCOMING
    WebUi Label: Log entries for unknown connection attempts
    Log entries for undefined incoming connection attempts."
  ::= { mGuardGRETunnelEntry 13 }

-- GSM_APN
mGuardGsmApn1 OBJECT-TYPE
  SYNTAX DisplayString
  ACCESS read-write
  STATUS mandatory
  DESCRIPTION
    "Variable name: GSM_APN
    WebUi Label: Access Point Name (APN) of the Provider
    The APN (Access Point Name) of your provider."
  ::= { mGuardGsmSim1 2 }

-- GSM_APN2
mGuardGsmApn2 OBJECT-TYPE
  SYNTAX DisplayString
  ACCESS read-write
  STATUS mandatory
  DESCRIPTION
    "Variable name: GSM_APN2
    WebUi Label: Access Point Name (APN) of the Provider
    The APN (Access Point Name) of your provider."
  ::= { mGuardGsmSim2 2 }

-- GSM_APN_OVERRIDE
mGuardApnOverride OBJECT-TYPE
  SYNTAX INTEGER {
    yes(1),
    no(2)
  }
  ACCESS read-write
  STATUS mandatory
  DESCRIPTION
    "Variable name: GSM_APN_OVERRIDE
    WebUi Label: Manual APN selection
    override OTA setting for APN of SIM1"
  ::= { mGuardGsmSim1 9 }

-- GSM_APN_OVERRIDE2
mGuardApnOverride2 OBJECT-TYPE
  SYNTAX INTEGER {
    yes(1),
    no(2)
  }
  ACCESS read-write
  STATUS mandatory
  DESCRIPTION
    "Variable name: GSM_APN_OVERRIDE2
    WebUi Label: Manual APN selection
    override OTA setting for APN of SIM2"
  ::= { mGuardGsmSim2 9 }

-- GSM_AUTH
mGuardGsmAuth1 OBJECT-TYPE
  SYNTAX INTEGER {
    yes(1),
    no(2)
  }
  ACCESS read-write
  STATUS mandatory
  DESCRIPTION
    "Variable name: GSM_AUTH
    WebUi Label: PPP authentication
    GSM PPP authentication"
  ::= { mGuardGsmSim1 6 }

-- GSM_AUTH2
mGuardGsmAuth2 OBJECT-TYPE
  SYNTAX INTEGER {
    yes(1),
    no(2)
  }
  ACCESS read-write
  STATUS mandatory
  DESCRIPTION
    "Variable name: GSM_AUTH2
    WebUi Label: PPP authentication
    GSM PPP authentication"
  ::= { mGuardGsmSim2 6 }

-- GSM_CDMA2000_INTERNATIONAL_PREFIX
mGuardGsmCdmaInternationalPrefix OBJECT-TYPE
  SYNTAX DisplayString
  ACCESS read-write
  STATUS mandatory
  DESCRIPTION
    "Variable name: GSM_CDMA2000_INTERNATIONAL_PREFIX
    WebUi Label: Prefix for non-automatic resolving of '+' code
    If mGuardGsmCdmaInternationalPrefixAuto is false, this prefix is used"
  ::= { mGuardGsm 21 }

-- GSM_CDMA2000_INTERNATIONAL_PREFIX_AUTO
mGuardGsmCdmaInternationalPrefixAuto OBJECT-TYPE
  SYNTAX INTEGER {
    yes(1),
    no(2)
  }
  ACCESS read-write
  STATUS mandatory
  DESCRIPTION
    "Variable name: GSM_CDMA2000_INTERNATIONAL_PREFIX_AUTO
    WebUi Label: Resolve '+' code for international access automatically
    Resolve '+' symbol as international exit code for CDMA phone numbers"
  ::= { mGuardGsm 22 }

-- GSM_DEBUG
mGuardGsmDebug OBJECT-TYPE
  SYNTAX INTEGER {
    yes(1),
    no(2)
  }
  ACCESS read-write
  STATUS mandatory
  DESCRIPTION
    "Variable name: GSM_DEBUG
    WebUi Label: Verbose mobile network logging
    GSM Enable Debug Logging (yes, no)"
  ::= { mGuardGsm 10 }

-- GSM_FALLBACK_RETURN_HOURS
mGuardGsmFallbackReturnHours OBJECT-TYPE
  SYNTAX INTEGER(0..24)
  ACCESS read-write
  STATUS mandatory
  DESCRIPTION
    "Variable name: GSM_FALLBACK_RETURN_HOURS
    WebUi Label: Switch back to the primary SIM after
    GSM: switch from fallback SIM to primary SIM after n Hours"
  ::= { mGuardGsm 5 }

-- GSM_NETWORK_2G
mGuardGsmNetwork2G OBJECT-TYPE
  SYNTAX INTEGER {
    yes(1),
    no(2)
  }
  ACCESS read-write
  STATUS mandatory
  DESCRIPTION
    "Variable name: GSM_NETWORK_2G
    WebUi Label: 2G (GPRS / EDGE / 1xRTT)
    GSM Enable 2G Network Connection (yes, no)"
  ::= { mGuardGsm 26 }

-- GSM_NETWORK_3G
mGuardGsmNetwork3G OBJECT-TYPE
  SYNTAX INTEGER {
    yes(1),
    no(2)
  }
  ACCESS read-write
  STATUS mandatory
  DESCRIPTION
    "Variable name: GSM_NETWORK_3G
    WebUi Label: 3G (UMTS / EVDO)
    GSM Enable 3G Network Connection (yes, no)"
  ::= { mGuardGsm 27 }

-- GSM_NETWORK_4G
mGuardGsmNetwork4G OBJECT-TYPE
  SYNTAX INTEGER {
    yes(1),
    no(2)
  }
  ACCESS read-write
  STATUS mandatory
  DESCRIPTION
    "Variable name: GSM_NETWORK_4G
    WebUi Label: 4G (LTE)
    GSM Enable 4G Network Connection (yes, no)"
  ::= { mGuardGsm 28 }

-- GSM_NETWORK_REGISTER_TOUT
mGuardGsmNetworkRegistrationTimeout OBJECT-TYPE
  SYNTAX INTEGER(20..600)
  ACCESS read-write
  STATUS mandatory
  DESCRIPTION
    "Variable name: GSM_NETWORK_REGISTER_TOUT
    WebUi Label: Mobile network registration timeout
    GSM: Timeout for the Mobile Network registration"
  ::= { mGuardGsm 20 }

-- GSM_NETWORK_TYPE
mGuardGsmNetworkType OBJECT-TYPE
  SYNTAX INTEGER {
    none(1),
    gsm(2),
    cdma(3)
  }
  ACCESS read-write
  STATUS mandatory
  DESCRIPTION
    "Variable name: GSM_NETWORK_TYPE
    WebUi Label: Mobile technology standard
    GSM: Mobile Network Connection Type"
  ::= { mGuardGsm 25 }

-- GSM_PASS
mGuardGsmPassword1 OBJECT-TYPE
  SYNTAX DisplayString
  ACCESS read-write
  STATUS mandatory
  DESCRIPTION
    "Variable name: GSM_PASS
    WebUi Label: PPP password
    Password to authenticate at the remote PPP peer via PAP."
  ::= { mGuardGsmSim1 5 }

-- GSM_PASS2
mGuardGsmPassword2 OBJECT-TYPE
  SYNTAX DisplayString
  ACCESS read-write
  STATUS mandatory
  DESCRIPTION
    "Variable name: GSM_PASS2
    WebUi Label: PPP password
    Password to authenticate at the remote PPP peer via PAP."
  ::= { mGuardGsmSim2 5 }

-- GSM_PIN
mGuardGsmPin1 OBJECT-TYPE
  SYNTAX DisplayString
  ACCESS read-write
  STATUS mandatory
  DESCRIPTION
    "Variable name: GSM_PIN
    WebUi Label: PIN of the SIM card
    The PIN to activate the SIM card."
  ::= { mGuardGsmSim1 1 }

-- GSM_PIN2
mGuardGsmPin2 OBJECT-TYPE
  SYNTAX DisplayString
  ACCESS read-write
  STATUS mandatory
  DESCRIPTION
    "Variable name: GSM_PIN2
    WebUi Label: PIN of the SIM card
    The PIN to activate the SIM card."
  ::= { mGuardGsmSim2 1 }

-- GSM_PPP_COMPRESSION
mGuardGsmPppCompression OBJECT-TYPE
  SYNTAX INTEGER {
    yes(1),
    no(2)
  }
  ACCESS read-write
  STATUS mandatory
  DESCRIPTION
    "Variable name: GSM_PPP_COMPRESSION
    WebUi Label: Allow compression
    GSM Enable PPP compression (yes, no)"
  ::= { mGuardGsm 15 }

-- GSM_PPP_MTU
mGuardGsmPppMtu OBJECT-TYPE
  SYNTAX INTEGER(128..16384)
  ACCESS read-write
  STATUS mandatory
  DESCRIPTION
    "Variable name: GSM_PPP_MTU
    WebUi Label: MTU Maximum Transfer Unit
    Sets the MTU used by the GSM pppd"
  ::= { mGuardGsm 14 }


-- GSM_PROBE table
mGuardGsmProbeTable OBJECT-TYPE
  SYNTAX SEQUENCE OF MGuardGsmProbeEntry
  ACCESS not-accessible
  STATUS mandatory
  DESCRIPTION
    "A table of GSM_PROBE"
  ::= { mGuardGsm 11 }

-- GSM_PROBE table entry
mGuardGsmProbeEntry OBJECT-TYPE
  SYNTAX MGuardGsmProbeEntry
  ACCESS not-accessible
  STATUS mandatory
  DESCRIPTION
    "An entry of GSM_PROBE"
  INDEX { mGuardGsmProbeIndex }
  ::= { mGuardGsmProbeTable 1 }

MGuardGsmProbeEntry ::= SEQUENCE {
  mGuardGsmProbeIndex                      INTEGER,
  mGuardGsmProbeRowStatus                  RowStatus,
  mGuardGsmProbeComment                    DisplayString,
  mGuardGsmProbeDestination                DisplayString,
  mGuardGsmProbeType                       INTEGER
}

-- GSM_PROBE table index
mGuardGsmProbeIndex OBJECT-TYPE
  SYNTAX INTEGER (1..2147483647)
  ACCESS not-accessible
  STATUS mandatory
  DESCRIPTION
    "Index to GSM_PROBE"
  ::= { mGuardGsmProbeEntry 1 }

-- GSM_PROBE row status
mGuardGsmProbeRowStatus OBJECT-TYPE
  SYNTAX RowStatus
  ACCESS read-write
  STATUS mandatory
  DESCRIPTION
    "RowStatus of GSM_PROBE"
  ::= { mGuardGsmProbeEntry 2 }

-- GSM_PROBE.COMMENT
mGuardGsmProbeComment OBJECT-TYPE
  SYNTAX DisplayString
  ACCESS read-write
  STATUS mandatory
  DESCRIPTION
    "Variable name: GSM_PROBE.COMMENT
    WebUi Label: Comment
    Commentary or name for this probe entry."
  ::= { mGuardGsmProbeEntry 3 }

-- GSM_PROBE.DESTINATION
mGuardGsmProbeDestination OBJECT-TYPE
  SYNTAX DisplayString
  ACCESS read-write
  STATUS mandatory
  DESCRIPTION
    "Variable name: GSM_PROBE.DESTINATION
    WebUi Label: Destination
    Sets the target host IP for this probe"
  ::= { mGuardGsmProbeEntry 4 }

-- GSM_PROBE.TYPE
mGuardGsmProbeType OBJECT-TYPE
  SYNTAX INTEGER {
    icmpping(1),
    dnsping(2),
    ikeping(3)
  }
  ACCESS read-write
  STATUS mandatory
  DESCRIPTION
    "Variable name: GSM_PROBE.TYPE
    WebUi Label: Type
    The operation type used to probe the GSM network."
  ::= { mGuardGsmProbeEntry 5 }

-- GSM_PROBE_FAILCOUNT
mGuardGsmProbeFailCount OBJECT-TYPE
  SYNTAX INTEGER(1..5)
  ACCESS read-write
  STATUS mandatory
  DESCRIPTION
    "Variable name: GSM_PROBE_FAILCOUNT
    WebUi Label: Number of times all probes need to fail before the mobile network
     connection is considered stalled
    Number of failures before the connection is considered stalled"
  ::= { mGuardGsm 12 }

-- GSM_PROBE_INTERVAL_MINUTES
mGuardGsmProbeIntervalMinutes OBJECT-TYPE
  SYNTAX INTEGER(1..60)
  ACCESS read-write
  STATUS mandatory
  DESCRIPTION
    "Variable name: GSM_PROBE_INTERVAL_MINUTES
    WebUi Label: Probe interval
    Interval between two probes"
  ::= { mGuardGsm 13 }

-- GSM_RELOGIN
mGuardGsmReloginEnable OBJECT-TYPE
  SYNTAX INTEGER {
    yes(1),
    no(2)
  }
  ACCESS read-write
  STATUS mandatory
  DESCRIPTION
    "Variable name: GSM_RELOGIN
    WebUi Label: Daily relogin
    GSM: enable daily relogin at the provider (yes, no)"
  ::= { mGuardGsm 6 }

-- GSM_RELOGIN_HOUR
mGuardGsmReloginHour OBJECT-TYPE
  SYNTAX INTEGER(0..23)
  ACCESS read-write
  STATUS mandatory
  DESCRIPTION
    "Variable name: GSM_RELOGIN_HOUR
    WebUi Label: Daily relogin at (hour)
    GSM: hour of daily relogin"
  ::= { mGuardGsm 7 }

-- GSM_RELOGIN_MINUTE
mGuardGsmReloginMinute OBJECT-TYPE
  SYNTAX INTEGER(0..59)
  ACCESS read-write
  STATUS mandatory
  DESCRIPTION
    "Variable name: GSM_RELOGIN_MINUTE
    WebUi Label: Daily relogin at (minute)
    GSM: minute of daily relogin"
  ::= { mGuardGsm 17 }

-- GSM_SHORT_MESSAGE_ALPHABET_RESTRICTED
mGuardGsmShortMessageAlphabetRestricted OBJECT-TYPE
  SYNTAX INTEGER {
    yes(1),
    no(2)
  }
  ACCESS read-write
  STATUS mandatory
  DESCRIPTION
    "Variable name: GSM_SHORT_MESSAGE_ALPHABET_RESTRICTED
    WebUi Label: Restrict outgoing text messages to basic character set
    Restrict the alphabet usable in short message service notifications"
  ::= { mGuardGsm 23 }

-- GSM_SIM_ENABLE
mGuardGsmSim1Enable OBJECT-TYPE
  SYNTAX INTEGER {
    yes(1),
    no(2)
  }
  ACCESS read-write
  STATUS mandatory
  DESCRIPTION
    "Variable name: GSM_SIM_ENABLE
    WebUi Label: Activation
    GSM Enable SIM 1 (yes, no)"
  ::= { mGuardGsmSim1 7 }

-- GSM_SIM_ENABLE2
mGuardGsmSim2Enable OBJECT-TYPE
  SYNTAX INTEGER {
    yes(1),
    no(2)
  }
  ACCESS read-write
  STATUS mandatory
  DESCRIPTION
    "Variable name: GSM_SIM_ENABLE2
    WebUi Label: Activation
    GSM Enable SIM 1 (yes, no)"
  ::= { mGuardGsmSim2 7 }

-- GSM_SIM_INIT_TOUT
mGuardGsmSimInitializationTimeout OBJECT-TYPE
  SYNTAX INTEGER(20..600)
  ACCESS read-write
  STATUS mandatory
  DESCRIPTION
    "Variable name: GSM_SIM_INIT_TOUT
    WebUi Label: SIM initialization timeout
    GSM: Timeout for the SIM initialization after entering the PIN"
  ::= { mGuardGsm 19 }

-- GSM_SIM_PROVIDER
mGuardGsmSim1Plmn OBJECT-TYPE
  SYNTAX INTEGER(0..999999)
  ACCESS read-write
  STATUS mandatory
  DESCRIPTION
    "Variable name: GSM_SIM_PROVIDER
    WebUi Label: Provider selection
    GSM SIM 1 PLMN Identification: Mobile Country Code (MCC) + Mobile
    Network Code (MNC)"
  ::= { mGuardGsmSim1 8 }

-- GSM_SIM_PROVIDER2
mGuardGsmSim2Plmn OBJECT-TYPE
  SYNTAX INTEGER(0..999999)
  ACCESS read-write
  STATUS mandatory
  DESCRIPTION
    "Variable name: GSM_SIM_PROVIDER2
    WebUi Label: Provider selection
    GSM SIM 2 PLMN Identification: Mobile Country Code (MCC) + Mobile
    Network Code (MNC)"
  ::= { mGuardGsmSim2 8 }

-- GSM_USER
mGuardGsmUser1 OBJECT-TYPE
  SYNTAX DisplayString
  ACCESS read-write
  STATUS mandatory
  DESCRIPTION
    "Variable name: GSM_USER
    WebUi Label: PPP login
    User name to authenticate at the remote PPP peer via PAP."
  ::= { mGuardGsmSim1 4 }

-- GSM_USER2
mGuardGsmUser2 OBJECT-TYPE
  SYNTAX DisplayString
  ACCESS read-write
  STATUS mandatory
  DESCRIPTION
    "Variable name: GSM_USER2
    WebUi Label: PPP login
    User name to authenticate at the remote PPP peer via PAP."
  ::= { mGuardGsmSim2 4 }

-- HM_RS2_SIG_CONNECTIVITY_ALARM
mGuardTResSignalRelaisConnectivityAlarm OBJECT-TYPE
  SYNTAX INTEGER {
    on(1),
    off(2)
  }
  ACCESS read-write
  STATUS mandatory
  DESCRIPTION
    "Variable name: HM_RS2_SIG_CONNECTIVITY_ALARM
    WebUi Label: Connectivity state of redundancy
    Enables/disables an alarm for the signaling relay of the Redundancy
    connectivity state"
  ::= { mGuardTResSignalRelais 8 }

-- HM_RS2_SIG_MODEM_ALARM
mGuardTResSignalRelaisModemConnectionAlarm OBJECT-TYPE
  SYNTAX INTEGER {
    on(1),
    off(2)
  }
  ACCESS read-write
  STATUS mandatory
  DESCRIPTION
    "Variable name: HM_RS2_SIG_MODEM_ALARM
    WebUi Label: Connection state of the modem
    Enables/disables an alarm if the modem is offline."
  ::= { mGuardTResSignalRelais 9 }

-- HM_RS2_SIG_PS2_ALARM
mGuardTResSignalRelaisPowerAlarm OBJECT-TYPE
  SYNTAX INTEGER {
    enable(1),
    disable(2)
  }
  ACCESS read-write
  STATUS mandatory
  DESCRIPTION
    "Variable name: HM_RS2_SIG_PS2_ALARM
    WebUi Label: Redundant power supply
    Enables/disables an alarm for the signaling relay of the power supply
    state."
  ::= { mGuardTResSignalRelais 4 }

-- HM_RS2_SIG_RELAY_MANUAL_STATE
mGuardTResSignalRelaisManualStat OBJECT-TYPE
  SYNTAX INTEGER {
    on(1),
    off(2)
  }
  ACCESS read-write
  STATUS mandatory
  DESCRIPTION
    "Variable name: HM_RS2_SIG_RELAY_MANUAL_STATE
    WebUi Label: Manual setting
    When set to on, this is the default, the signaling relay is opened.
    When set to off the relay is closed."
  ::= { mGuardTResSignalRelais 6 }

-- HM_RS2_SIG_RELAY_MODE
mGuardTResSignalRelaisMode OBJECT-TYPE
  SYNTAX INTEGER {
    standard(1),
    manual(2)
  }
  ACCESS read-write
  STATUS mandatory
  DESCRIPTION
    "Variable name: HM_RS2_SIG_RELAY_MODE
    WebUi Label: Operation mode
    When set to standard, this is the default, the signaling relay shows
    the state of hmRS2SigRelayState. When set to manual, the relay is
    controlled by the configured Manual State."
  ::= { mGuardTResSignalRelais 5 }

-- HM_RS2_SIG_TEMP_ALARM
mGuardTResSignalRelaisTempAlarm OBJECT-TYPE
  SYNTAX INTEGER {
    on(1),
    off(2)
  }
  ACCESS read-write
  STATUS mandatory
  DESCRIPTION
    "Variable name: HM_RS2_SIG_TEMP_ALARM
    WebUi Label: Temperature condition
    Enables/disables an alarm for the signaling relay of the temperature
    condition"
  ::= { mGuardTResSignalRelais 7 }

-- HM_TEMP_MAX
mGuardTResIndustrialTempHiLimit OBJECT-TYPE
  SYNTAX INTEGER(-40..999)
  ACCESS read-write
  STATUS mandatory
  DESCRIPTION
    "Variable name: HM_TEMP_MAX
    WebUi Label: System temperature
    Upper limit of allowed system temperature."
  ::= { mGuardTResIndustrialTemperature 2 }

-- HM_TEMP_MIN
mGuardTResIndustrialTempLowLimit OBJECT-TYPE
  SYNTAX INTEGER(-40..999)
  ACCESS read-write
  STATUS mandatory
  DESCRIPTION
    "Variable name: HM_TEMP_MIN
    WebUi Label: System temperature
    Lower limit of allowed system temperature."
  ::= { mGuardTResIndustrialTemperature 3 }

-- HTTPS_AUTH_CLIENT
mGuardHTTPSX509AuthClnt OBJECT-TYPE
  SYNTAX INTEGER {
    no(1),
    may(2),
    must(3)
  }
  ACCESS read-write
  STATUS mandatory
  DESCRIPTION
    "Variable name: HTTPS_AUTH_CLIENT
    WebUi Label: User authentication method
    Defines how to identify HTTPS clients: no: login page may: login page
    or X.509 client certificate must: client certificate"
  ::= { mGuardHTTPSX509 3 }


-- HTTPS_CA_CERTS table
mGuardHTTPSX509CARefsTable OBJECT-TYPE
  SYNTAX SEQUENCE OF MGuardHTTPSX509CARefsEntry
  ACCESS not-accessible
  STATUS mandatory
  DESCRIPTION
    "A table of HTTPS_CA_CERTS"
  ::= { mGuardHTTPSX509 4 }

-- HTTPS_CA_CERTS table entry
mGuardHTTPSX509CARefsEntry OBJECT-TYPE
  SYNTAX MGuardHTTPSX509CARefsEntry
  ACCESS not-accessible
  STATUS mandatory
  DESCRIPTION
    "An entry of HTTPS_CA_CERTS"
  INDEX { mGuardHTTPSX509CARefsIdx }
  ::= { mGuardHTTPSX509CARefsTable 1 }

MGuardHTTPSX509CARefsEntry ::= SEQUENCE {
  mGuardHTTPSX509CARefsIdx                 INTEGER,
  mGuardHTTPSX509CARefsRowStatus           RowStatus,
  mGuardHTTPSX509CARefsNewRef              OBJECT IDENTIFIER
}

-- HTTPS_CA_CERTS table index
mGuardHTTPSX509CARefsIdx OBJECT-TYPE
  SYNTAX INTEGER (1..2147483647)
  ACCESS not-accessible
  STATUS mandatory
  DESCRIPTION
    "Index to HTTPS_CA_CERTS"
  ::= { mGuardHTTPSX509CARefsEntry 1 }

-- HTTPS_CA_CERTS row status
mGuardHTTPSX509CARefsRowStatus OBJECT-TYPE
  SYNTAX RowStatus
  ACCESS read-write
  STATUS mandatory
  DESCRIPTION
    "RowStatus of HTTPS_CA_CERTS"
  ::= { mGuardHTTPSX509CARefsEntry 10 }

-- HTTPS_CA_CERTS.CERTIFICATE_REF reference
mGuardHTTPSX509CARefsNewRef OBJECT-TYPE
  SYNTAX OBJECT IDENTIFIER
  ACCESS read-write
  STATUS mandatory
  DESCRIPTION
    "Variable name: HTTPS_CA_CERTS.CERTIFICATE_REF
    WebUi Label: CA certificate
    When this object contains the OID of an 'mGuardCertsCAIndex' object,
    the corresponding CA certificate is used to validate the remote peer."
  ::= { mGuardHTTPSX509CARefsEntry 11 }

-- HTTPS_REMOTE_ACCESS_RULES
mGuardHTTPSRemoteUUID OBJECT-TYPE
  SYNTAX DisplayString
  ACCESS read-only
  STATUS mandatory
  DESCRIPTION
    "Variable name: HTTPS_REMOTE_ACCESS_RULES
    WebUi Label: Allowed networks
    Universally Unique Identifier (UUID, RFC 4122) used for
    mGuardHTTPSRemoteFWRuleTable logging."
  ::= { mGuardHTTPSRemoteAccess 4 }


-- HTTPS_REMOTE_ACCESS_RULES table
mGuardHTTPSRemoteFWRuleTable OBJECT-TYPE
  SYNTAX SEQUENCE OF MGuardHTTPSRemoteFWRuleEntry
  ACCESS not-accessible
  STATUS mandatory
  DESCRIPTION
    "A table of HTTPS_REMOTE_ACCESS_RULES"
  ::= { mGuardHTTPSRemoteAccess 3 }

-- HTTPS_REMOTE_ACCESS_RULES table entry
mGuardHTTPSRemoteFWRuleEntry OBJECT-TYPE
  SYNTAX MGuardHTTPSRemoteFWRuleEntry
  ACCESS not-accessible
  STATUS mandatory
  DESCRIPTION
    "An entry of HTTPS_REMOTE_ACCESS_RULES"
  INDEX { mGuardHTTPSFWruleIndex }
  ::= { mGuardHTTPSRemoteFWRuleTable 1 }

MGuardHTTPSRemoteFWRuleEntry ::= SEQUENCE {
  mGuardHTTPSFWruleIndex                   INTEGER,
  mGuardHTTPSFWsourceIP                    DisplayString,
  mGuardHTTPSFWinterface                   INTEGER,
  mGuardHTTPSFWtarget                      INTEGER,
  mGuardHTTPSFWlog                         INTEGER,
  mGuardHTTPSFWRowStatus                   RowStatus,
  mGuardHTTPSFWcomment                     DisplayString,
  mGuardHTTPSFWfromMAC                     MacAddress
}

-- HTTPS_REMOTE_ACCESS_RULES table index
mGuardHTTPSFWruleIndex OBJECT-TYPE
  SYNTAX INTEGER (1..2147483647)
  ACCESS not-accessible
  STATUS mandatory
  DESCRIPTION
    "Index to HTTPS_REMOTE_ACCESS_RULES"
  ::= { mGuardHTTPSRemoteFWRuleEntry 1 }

-- HTTPS_REMOTE_ACCESS_RULES row status
mGuardHTTPSFWRowStatus OBJECT-TYPE
  SYNTAX RowStatus
  ACCESS read-write
  STATUS mandatory
  DESCRIPTION
    "RowStatus of HTTPS_REMOTE_ACCESS_RULES"
  ::= { mGuardHTTPSRemoteFWRuleEntry 6 }

-- HTTPS_REMOTE_ACCESS_RULES.COMMENT
mGuardHTTPSFWcomment OBJECT-TYPE
  SYNTAX DisplayString
  ACCESS read-write
  STATUS mandatory
  DESCRIPTION
    "Variable name: HTTPS_REMOTE_ACCESS_RULES.COMMENT
    WebUi Label: Comment
    Commentary or name for this rule."
  ::= { mGuardHTTPSRemoteFWRuleEntry 7 }

-- HTTPS_REMOTE_ACCESS_RULES.LOG
mGuardHTTPSFWlog OBJECT-TYPE
  SYNTAX INTEGER {
    yes(1),
    no(2)
  }
  ACCESS read-write
  STATUS mandatory
  DESCRIPTION
    "Variable name: HTTPS_REMOTE_ACCESS_RULES.LOG
    WebUi Label: Log
    Log packets matching this rule ?"
  ::= { mGuardHTTPSRemoteFWRuleEntry 5 }

-- HTTPS_REMOTE_ACCESS_RULES.FROM_IP
mGuardHTTPSFWsourceIP OBJECT-TYPE
  SYNTAX DisplayString
  ACCESS read-write
  STATUS mandatory
  DESCRIPTION
    "Variable name: HTTPS_REMOTE_ACCESS_RULES.FROM_IP
    WebUi Label: From IP
    The rule's source IP address"
  ::= { mGuardHTTPSRemoteFWRuleEntry 2 }

-- HTTPS_REMOTE_ACCESS_RULES.INTERFACE_DEV
mGuardHTTPSFWinterface OBJECT-TYPE
  SYNTAX INTEGER {
    extern(1),
    intern(2),
    extern2(3),
    dialin(4),
    viaipsec(5),
    dmz0(6),
    viagre(7)
  }
  ACCESS read-write
  STATUS mandatory
  DESCRIPTION
    "Variable name: HTTPS_REMOTE_ACCESS_RULES.INTERFACE_DEV
    WebUi Label: Interface
    The network interface the rule belongs to (extern/intern)."
  ::= { mGuardHTTPSRemoteFWRuleEntry 3 }

-- HTTPS_REMOTE_ACCESS_RULES.FROM_MAC
mGuardHTTPSFWfromMAC OBJECT-TYPE
  SYNTAX MacAddress
  ACCESS read-write
  STATUS mandatory
  DESCRIPTION
    "Variable name: HTTPS_REMOTE_ACCESS_RULES.FROM_MAC
    WebUi Label: From MAC
    The rule's source MAC address."
  ::= { mGuardHTTPSRemoteFWRuleEntry 8 }

-- HTTPS_REMOTE_ACCESS_RULES.TARGET
mGuardHTTPSFWtarget OBJECT-TYPE
  SYNTAX INTEGER {
    accept(1),
    reject(2),
    drop(3)
  }
  ACCESS read-write
  STATUS mandatory
  DESCRIPTION
    "Variable name: HTTPS_REMOTE_ACCESS_RULES.TARGET
    WebUi Label: Action
    The target of the rule (accept/reject/drop)."
  ::= { mGuardHTTPSRemoteFWRuleEntry 4 }

-- HTTPS_REMOTE_ENABLE
mGuardHTTPSRemoteEnable OBJECT-TYPE
  SYNTAX INTEGER {
    yes(1),
    no(2)
  }
  ACCESS read-write
  STATUS mandatory
  DESCRIPTION
    "Variable name: HTTPS_REMOTE_ENABLE
    WebUi Label: Enable HTTPS remote access
    Value to control HTTPS remote access: yes: enabled no: disabled"
  ::= { mGuardHTTPSRemoteAccess 1 }

-- HTTPS_REMOTE_LISTENPORT
mGuardHTTPSRemotePort OBJECT-TYPE
  SYNTAX DisplayString
  ACCESS read-write
  STATUS mandatory
  DESCRIPTION
    "Variable name: HTTPS_REMOTE_LISTENPORT
    WebUi Label: Remote HTTPS TCP port
    Port for HTTPS remote Access (regularly 443), service names allowed."
  ::= { mGuardHTTPSRemoteAccess 2 }

-- HTTPS_SERVER_CERT_REF
mGuardHTTPSX509LocalCertValue OBJECT-TYPE
  SYNTAX INTEGER {
    none(1)
  }
  ACCESS read-write
  STATUS mandatory
  DESCRIPTION
    "Variable name: HTTPS_SERVER_CERT_REF
    WebUi Label: HTTPS server certificate
    This object is effective if and only if the
    'mGuardHTTPSX509LocalCertRef' object contains the OID of this object.
    When this object is read, it always returns the value 'none'. When the
    value 'none' is written to this object, no local machine certificate
    is used."
  ::= { mGuardHTTPSX509 7 }

-- HTTPS_SERVER_CERT_REF reference
mGuardHTTPSX509LocalCertRef OBJECT-TYPE
  SYNTAX OBJECT IDENTIFIER
  ACCESS read-write
  STATUS mandatory
  DESCRIPTION
    "Variable name: HTTPS_SERVER_CERT_REF
    WebUi Label: HTTPS server certificate
    When this object contains the OID of an 'mGuardCertsLocalIndex'
    object, the corresponding X.509 certificate and private key is used to
    identify this site. To select a local machine certificate in this
    manner, write the OID of the corresponding 'mGuardCertsLocalIndex'
    object to this object. To disable this feature, set the
    'mGuardHTTPSX509LocalCertValue' object."
  ::= { mGuardHTTPSX509 8 }


-- HTTPS_X509_AUTH table
mGuardHTTPSX509AuthSubjTable OBJECT-TYPE
  SYNTAX SEQUENCE OF MGuardHTTPSX509AuthSubjEntry
  ACCESS not-accessible
  STATUS mandatory
  DESCRIPTION
    "A table of HTTPS_X509_AUTH"
  ::= { mGuardHTTPSX509 5 }

-- HTTPS_X509_AUTH table entry
mGuardHTTPSX509AuthSubjEntry OBJECT-TYPE
  SYNTAX MGuardHTTPSX509AuthSubjEntry
  ACCESS not-accessible
  STATUS mandatory
  DESCRIPTION
    "An entry of HTTPS_X509_AUTH"
  INDEX { mGuardHTTPSX509AuthSubjIdx }
  ::= { mGuardHTTPSX509AuthSubjTable 1 }

MGuardHTTPSX509AuthSubjEntry ::= SEQUENCE {
  mGuardHTTPSX509AuthSubjIdx               INTEGER,
  mGuardHTTPSX509AuthSubjSubject           DisplayString,
  mGuardHTTPSX509AuthSubjUser              INTEGER,
  mGuardHTTPSX509AuthSubjRowStatus         RowStatus
}

-- HTTPS_X509_AUTH table index
mGuardHTTPSX509AuthSubjIdx OBJECT-TYPE
  SYNTAX INTEGER (1..2147483647)
  ACCESS not-accessible
  STATUS mandatory
  DESCRIPTION
    "Index to HTTPS_X509_AUTH"
  ::= { mGuardHTTPSX509AuthSubjEntry 1 }

-- HTTPS_X509_AUTH row status
mGuardHTTPSX509AuthSubjRowStatus OBJECT-TYPE
  SYNTAX RowStatus
  ACCESS read-write
  STATUS mandatory
  DESCRIPTION
    "RowStatus of HTTPS_X509_AUTH"
  ::= { mGuardHTTPSX509AuthSubjEntry 10 }

-- HTTPS_X509_AUTH.USER
mGuardHTTPSX509AuthSubjUser OBJECT-TYPE
  SYNTAX INTEGER {
    root(1),
    admin(2),
    netadmin(3),
    audit(4),
    user(5)
  }
  ACCESS read-write
  STATUS mandatory
  DESCRIPTION
    "Variable name: HTTPS_X509_AUTH.USER
    WebUi Label: Authorized for access as
    User being authenticated by mGuardHTTPSX509AuthSubjSubject."
  ::= { mGuardHTTPSX509AuthSubjEntry 3 }

-- HTTPS_X509_AUTH.SUBJECT
mGuardHTTPSX509AuthSubjSubject OBJECT-TYPE
  SYNTAX DisplayString
  ACCESS read-write
  STATUS mandatory
  DESCRIPTION
    "Variable name: HTTPS_X509_AUTH.SUBJECT
    WebUi Label: X.509 subject
    The X.509 subject or subjects that needs to be included in
    certificate."
  ::= { mGuardHTTPSX509AuthSubjEntry 2 }


-- HTTPS_X509_AUTH_BLOB table
mGuardHTTPSX509AuthCertTable OBJECT-TYPE
  SYNTAX SEQUENCE OF MGuardHTTPSX509AuthCertEntry
  ACCESS not-accessible
  STATUS mandatory
  DESCRIPTION
    "A table of HTTPS_X509_AUTH_BLOB"
  ::= { mGuardHTTPSX509 6 }

-- HTTPS_X509_AUTH_BLOB table entry
mGuardHTTPSX509AuthCertEntry OBJECT-TYPE
  SYNTAX MGuardHTTPSX509AuthCertEntry
  ACCESS not-accessible
  STATUS mandatory
  DESCRIPTION
    "An entry of HTTPS_X509_AUTH_BLOB"
  INDEX { mGuardHTTPSX509AuthCertIdx }
  ::= { mGuardHTTPSX509AuthCertTable 1 }

MGuardHTTPSX509AuthCertEntry ::= SEQUENCE {
  mGuardHTTPSX509AuthCertIdx               INTEGER,
  mGuardHTTPSX509AuthCertUsr               INTEGER,
  mGuardHTTPSX509AuthCertRowStatus         RowStatus,
  mGuardHTTPSX509AuthCertNewRef            OBJECT IDENTIFIER
}

-- HTTPS_X509_AUTH_BLOB table index
mGuardHTTPSX509AuthCertIdx OBJECT-TYPE
  SYNTAX INTEGER (1..2147483647)
  ACCESS not-accessible
  STATUS mandatory
  DESCRIPTION
    "Index to HTTPS_X509_AUTH_BLOB"
  ::= { mGuardHTTPSX509AuthCertEntry 1 }

-- HTTPS_X509_AUTH_BLOB row status
mGuardHTTPSX509AuthCertRowStatus OBJECT-TYPE
  SYNTAX RowStatus
  ACCESS read-write
  STATUS mandatory
  DESCRIPTION
    "RowStatus of HTTPS_X509_AUTH_BLOB"
  ::= { mGuardHTTPSX509AuthCertEntry 10 }

-- HTTPS_X509_AUTH_BLOB.CERTIFICATE_REF reference
mGuardHTTPSX509AuthCertNewRef OBJECT-TYPE
  SYNTAX OBJECT IDENTIFIER
  ACCESS read-write
  STATUS mandatory
  DESCRIPTION
    "Variable name: HTTPS_X509_AUTH_BLOB.CERTIFICATE_REF
    WebUi Label: Client certificate
    When this object contains the OID of an 'mGuardCertsRemoteIndex'
    object, the corresponding remote certificate is used for the HTTPS
    X.509 authentication."
  ::= { mGuardHTTPSX509AuthCertEntry 11 }

-- HTTPS_X509_AUTH_BLOB.USER
mGuardHTTPSX509AuthCertUsr OBJECT-TYPE
  SYNTAX INTEGER {
    root(1),
    admin(2),
    netadmin(3),
    audit(4),
    user(5)
  }
  ACCESS read-write
  STATUS mandatory
  DESCRIPTION
    "Variable name: HTTPS_X509_AUTH_BLOB.USER
    WebUi Label: Authorized for access as
    The user authenticated by the X.509 certificate."
  ::= { mGuardHTTPSX509AuthCertEntry 3 }

-- ICMP_LENGTH_MAX
mGuardFirewallICMPLengthMax OBJECT-TYPE
  SYNTAX INTEGER(40..65535)
  ACCESS read-write
  STATUS mandatory
  DESCRIPTION
    "Variable name: ICMP_LENGTH_MAX
    WebUi Label: Maximum size of 'ping' packets (ICMP echo request)
    Maximum packet size for reassembled ICMP echo request (ping)"
  ::= { mGuardFirewallExtended 17 }

-- ICMP_LIMIT_EXT
mGuardFirewallICMPLimitExt OBJECT-TYPE
  SYNTAX INTEGER
  ACCESS read-write
  STATUS mandatory
  DESCRIPTION
    "Variable name: ICMP_LIMIT_EXT
    WebUi Label: Incoming
    Maximum number of incoming ping frames (ICMP Echo Request) per second"
  ::= { mGuardFirewallExtended 5 }

-- ICMP_LIMIT_INT
mGuardFirewallICMPLimitInt OBJECT-TYPE
  SYNTAX INTEGER
  ACCESS read-write
  STATUS mandatory
  DESCRIPTION
    "Variable name: ICMP_LIMIT_INT
    WebUi Label: Outgoing
    Maximum number of outgoing ping frames (ICMP Echo Request) per second"
  ::= { mGuardFirewallExtended 4 }

-- IGMP_QUERY
mGuardIgmpQuery OBJECT-TYPE
  SYNTAX INTEGER {
    off(1),
    v1(2),
    v2(3)
  }
  ACCESS read-write
  STATUS mandatory
  DESCRIPTION
    "Variable name: IGMP_QUERY
    WebUi Label: IGMP query
    Configures the type of IGMP queries"
  ::= { mGuardIgmp 3 }

-- IGMP_QUERY_INTERVAL
mGuardIgmpQueryInterval OBJECT-TYPE
  SYNTAX INTEGER(10..3600)
  ACCESS read-write
  STATUS mandatory
  DESCRIPTION
    "Variable name: IGMP_QUERY_INTERVAL
    WebUi Label: IGMP query interval
    Configures the interval for IGMP queries"
  ::= { mGuardIgmp 4 }

-- IGMP_SNOOP
mGuardIgmpSnoop OBJECT-TYPE
  SYNTAX INTEGER {
    yes(1),
    no(2)
  }
  ACCESS read-write
  STATUS mandatory
  DESCRIPTION
    "Variable name: IGMP_SNOOP
    WebUi Label: IGMP snooping
    Enables IGMP snooping"
  ::= { mGuardIgmp 1 }

-- IGMP_SNOOP_AGING
mGuardIgmpSnoopAging OBJECT-TYPE
  SYNTAX INTEGER(30..3600)
  ACCESS read-write
  STATUS mandatory
  DESCRIPTION
    "Variable name: IGMP_SNOOP_AGING
    WebUi Label: IGMP snoop aging
    Configures the interval to clear group memberships"
  ::= { mGuardIgmp 2 }

-- IGNORE_CERT_TIMES
mGuardCertsCheckTime OBJECT-TYPE
  SYNTAX INTEGER {
    always(1),
    when-synced(2),
    never(3)
  }
  ACCESS read-write
  STATUS mandatory
  DESCRIPTION
    "Variable name: IGNORE_CERT_TIMES
    WebUi Label: Check the validity period of certificates and CRLs
    When to require validity of Certificates and CRLs."
  ::= { mGuardCerts 5 }

-- IP_CONNTRACK_FTP
mGuardFirewallEnableConntrackFTP OBJECT-TYPE
  SYNTAX INTEGER {
    yes(1),
    no(2)
  }
  ACCESS read-write
  STATUS mandatory
  DESCRIPTION
    "Variable name: IP_CONNTRACK_FTP
    WebUi Label: FTP
    Enable active FTP NAT/Connection Tracking support"
  ::= { mGuardFirewallExtended 6 }

-- IP_CONNTRACK_H323
mGuardFirewallConntrackH323 OBJECT-TYPE
  SYNTAX INTEGER {
    yes(1),
    no(2)
  }
  ACCESS read-write
  STATUS mandatory
  DESCRIPTION
    "Variable name: IP_CONNTRACK_H323
    WebUi Label: H.323
    Enable H323 NAT/Connection Tracking support"
  ::= { mGuardFirewallExtended 12 }

-- IP_CONNTRACK_IRC
mGuardFirewallConntrackIRC OBJECT-TYPE
  SYNTAX INTEGER {
    yes(1),
    no(2)
  }
  ACCESS read-write
  STATUS mandatory
  DESCRIPTION
    "Variable name: IP_CONNTRACK_IRC
    WebUi Label: IRC
    Enable IRC NAT/Connection Tracking support"
  ::= { mGuardFirewallExtended 7 }

-- IP_CONNTRACK_MAX
mGuardFirewallIPConntrackMax OBJECT-TYPE
  SYNTAX INTEGER
  ACCESS read-write
  STATUS mandatory
  DESCRIPTION
    "Variable name: IP_CONNTRACK_MAX
    WebUi Label: Maximum table size
    Maximum size of connection tracking table"
  ::= { mGuardFirewallExtended 1 }

-- IP_CONNTRACK_OPC
mGuardFirewallConntrackOPC OBJECT-TYPE
  SYNTAX INTEGER {
    yes(1),
    no(2)
  }
  ACCESS read-write
  STATUS mandatory
  DESCRIPTION
    "Variable name: IP_CONNTRACK_OPC
    WebUi Label: OPC Classic
    Enable OPC NAT/Connection Tracking support"
  ::= { mGuardFirewallExtended 23 }

-- IP_CONNTRACK_OPC_SANITY
mGuardFirewallConntrackOPCSanity OBJECT-TYPE
  SYNTAX INTEGER {
    yes(1),
    no(2)
  }
  ACCESS read-write
  STATUS mandatory
  DESCRIPTION
    "Variable name: IP_CONNTRACK_OPC_SANITY
    WebUi Label: Sanity check for OPC Classic
    Enable sanity checks for data on tracked OPC connections"
  ::= { mGuardFirewallExtended 24 }

-- IP_CONNTRACK_OPC_TIMEOUT
mGuardFirewallConntrackOPCTimeout OBJECT-TYPE
  SYNTAX INTEGER(1..86400)
  ACCESS read-write
  STATUS mandatory
  DESCRIPTION
    "Variable name: IP_CONNTRACK_OPC_TIMEOUT
    WebUi Label: Timeout for OPC Classic connection expectations
    Lifetime of expectations for new OPC connections, which will be
    handled as childs from tracked OPC connections"
  ::= { mGuardFirewallExtended 25 }

-- IP_CONNTRACK_PPTP
mGuardFirewallConntrackPPTP OBJECT-TYPE
  SYNTAX INTEGER {
    yes(1),
    no(2)
  }
  ACCESS read-write
  STATUS mandatory
  DESCRIPTION
    "Variable name: IP_CONNTRACK_PPTP
    WebUi Label: PPTP
    Enable PPTP NAT/Connection Tracking support"
  ::= { mGuardFirewallExtended 8 }

-- IP_CONNTRACK_SIP
mGuardFirewallConntrackSIP OBJECT-TYPE
  SYNTAX INTEGER {
    yes(1),
    no(2)
  }
  ACCESS read-write
  STATUS mandatory
  DESCRIPTION
    "Variable name: IP_CONNTRACK_SIP
    WebUi Label: SIP
    Enable SIP NAT/Connection Tracking support"
  ::= { mGuardFirewallExtended 15 }

-- IP_CONNTRACK_TCP_TIMEOUT_CLOSE_WAIT
mGuardFWConntrackTcpTimeoutCWait OBJECT-TYPE
  SYNTAX INTEGER(0..86400)
  ACCESS read-write
  STATUS mandatory
  DESCRIPTION
    "Variable name: IP_CONNTRACK_TCP_TIMEOUT_CLOSE_WAIT
    WebUi Label: Timeout for closed TCP connections
    Timeout in conntrack table for closed TCP connections"
  ::= { mGuardFirewallExtended 18 }

-- IP_CONNTRACK_TCP_TIMEOUT_ESTABLISHED
mGuardFWConntrackTcpTimeoutEstab OBJECT-TYPE
  SYNTAX INTEGER
  ACCESS read-write
  STATUS mandatory
  DESCRIPTION
    "Variable name: IP_CONNTRACK_TCP_TIMEOUT_ESTABLISHED
    WebUi Label: Timeout for established TCP connections
    Timeout in conntrack table for established TCP connections"
  ::= { mGuardFirewallExtended 14 }

-- IP_SYNFLOOD_LIMIT_EXT
mGuardFirewallIPSynfloodLimitExt OBJECT-TYPE
  SYNTAX INTEGER
  ACCESS read-write
  STATUS mandatory
  DESCRIPTION
    "Variable name: IP_SYNFLOOD_LIMIT_EXT
    WebUi Label: Incoming
    Maximum number of new incoming TCP connections (SYN) per second"
  ::= { mGuardFirewallExtended 3 }

-- IP_SYNFLOOD_LIMIT_INT
mGuardFirewallIPSynfloodLimitInt OBJECT-TYPE
  SYNTAX INTEGER
  ACCESS read-write
  STATUS mandatory
  DESCRIPTION
    "Variable name: IP_SYNFLOOD_LIMIT_INT
    WebUi Label: Outgoing
    Maximum number of new outgoing TCP connections (SYN) per second"
  ::= { mGuardFirewallExtended 2 }

-- IP_UNCLEAN_MATCH
mGuardFirewallIpUncleanMatch OBJECT-TYPE
  SYNTAX INTEGER {
    yes(1),
    no(2)
  }
  ACCESS read-write
  STATUS mandatory
  DESCRIPTION
    "Variable name: IP_UNCLEAN_MATCH
    WebUi Label: Enable TCP/UDP/ICMP consistency checks
    Enable IP Unclean Match"
  ::= { mGuardFirewallExtended 13 }

-- KBD_KEYMAP_I386
mGuardKeyboardKeymapI386 OBJECT-TYPE
  SYNTAX INTEGER {
    azerty-azerty(1),
    azerty-be-latin1(2),
    azerty-fr(3),
    azerty-fr-latin1(4),
    azerty-fr-latin9(5),
    azerty-fr-pc(6),
    azerty-wangbe(7),
    azerty-wangbe2(8),
    dvorak-ANSI-dvorak(9),
    dvorak-dvorak(10),
    dvorak-dvorak-l(11),
    dvorak-dvorak-r(12),
    dvorak-no(13),
    fgGIod-tr-f-latin5(14),
    fgGIod-trf(15),
    qwerty-bashkir(16),
    qwerty-bg-cp1251(17),
    qwerty-bg-cp855(18),
    qwerty-bg-bds-cp1251(19),
    qwerty-bg-bds-utf8(20),
    qwerty-bg-pho-cp1251(21),
    qwerty-bg-pho-utf8(22),
    qwerty-br-abnt(23),
    qwerty-br-abnt2(24),
    qwerty-br-latin1-abnt2(25),
    qwerty-br-latin1-us(26),
    qwerty-by(27),
    qwerty-by-cp1251(28),
    qwerty-bywin-cp1251(29),
    qwerty-cf(30),
    qwerty-cz(31),
    qwerty-cz-cp1250(32),
    qwerty-cz-lat2(33),
    qwerty-cz-lat2-prog(34),
    qwerty-dk(35),
    qwerty-dk-latin1(36),
    qwerty-es(37),
    qwerty-es-cp850(38),
    qwerty-et(39),
    qwerty-et-nodeadkeys(40),
    qwerty-fi(41),
    qwerty-fi-latin1(42),
    qwerty-fi-latin9(43),
    qwerty-gr(44),
    qwerty-gr-pc(45),
    qwerty-hu101(46),
    qwerty-il(47),
    qwerty-il-heb(48),
    qwerty-il-phonetic(49),
    qwerty-is-latin1(50),
    qwerty-is-latin1-us(51),
    qwerty-it(52),
    qwerty-it-ibm(53),
    qwerty-it2(54),
    qwerty-jp106(55),
    qwerty-kazakh(56),
    qwerty-kyrgyz(57),
    qwerty-la-latin1(58),
    qwerty-lt(59),
    qwerty-lt-baltic(60),
    qwerty-lt-l4(61),
    qwerty-mk(62),
    qwerty-mk-cp1251(63),
    qwerty-mk-utf(64),
    qwerty-mk0(65),
    qwerty-nl(66),
    qwerty-nl2(67),
    qwerty-no(68),
    qwerty-no-latin1(69),
    qwerty-pc110(70),
    qwerty-pl(71),
    qwerty-pl1(72),
    qwerty-pl2(73),
    qwerty-pl3(74),
    qwerty-pl4(75),
    qwerty-pt-latin1(76),
    qwerty-pt-latin9(77),
    qwerty-ro(78),
    qwerty-ro-std(79),
    qwerty-ro-win(80),
    qwerty-ru(81),
    qwerty-ru-cp1251(82),
    qwerty-ru-ms(83),
    qwerty-ru-yawerty(84),
    qwerty-ru1(85),
    qwerty-ru2(86),
    qwerty-ru3(87),
    qwerty-ru4(88),
    qwerty-ru-win(89),
    qwerty-ruwin-alt-CP1251(90),
    qwerty-ruwin-alt-KOI8-R(91),
    qwerty-ruwin-alt-UTF-8(92),
    qwerty-ruwin-cplk-CP1251(93),
    qwerty-ruwin-cplk-KOI8-R(94),
    qwerty-ruwin-cplk-UTF-8(95),
    qwerty-ruwin-ct-sh-CP1251(96),
    qwerty-ruwin-ct-sh-KOI8-R(97),
    qwerty-ruwin-ct-sh-UTF-8(98),
    qwerty-ruwin-ctrl-CP1251(99),
    qwerty-ruwin-ctrl-KOI8-R(100),
    qwerty-ruwin-ctrl-UTF-8(101),
    qwerty-se-fi-ir209(102),
    qwerty-se-fi-lat6(103),
    qwerty-se-ir209(104),
    qwerty-se-lat6(105),
    qwerty-sk-prog-qwerty(106),
    qwerty-sk-qwerty(107),
    qwerty-sr-cy(108),
    qwerty-sv-latin1(109),
    qwerty-tr-q-latin5(110),
    qwerty-tralt(111),
    qwerty-trf(112),
    qwerty-trq(113),
    qwerty-ttwin-alt-UTF-8(114),
    qwerty-ttwin-cplk-UTF-8(115),
    qwerty-ttwin-ct-sh-UTF-8(116),
    qwerty-ttwin-ctrl-UTF-8(117),
    qwerty-ua(118),
    qwerty-ua-cp1251(119),
    qwerty-ua-utf(120),
    qwerty-ua-utf-ws(121),
    qwerty-ua-ws(122),
    qwerty-uk(123),
    qwerty-us(124),
    qwerty-us-acentos(125),
    qwertz-croat(126),
    qwertz-cz(127),
    qwertz-cz-us-qwertz(128),
    qwertz-de(129),
    qwertz-de-latin1(130),
    qwertz-de-latin1-nodeadkeys(131),
    qwertz-de-CH-latin1(132),
    qwertz-fr-CH(133),
    qwertz-fr-CH-latin1(134),
    qwertz-hu(135),
    qwertz-sg(136),
    qwertz-sg-latin1(137),
    qwertz-sg-latin1-lk450(138),
    qwertz-sk-prog-qwertz(139),
    qwertz-sk-qwertz(140),
    qwertz-slovene(141)
  }
  ACCESS read-write
  STATUS mandatory
  DESCRIPTION
    "Variable name: KBD_KEYMAP_I386
    WebUi Label: Keyboard layout
    I386 key mapping."
  ::= { mGuardKeyboardSettings 3 }

-- L2REDUNDANCY
mGuardL2RedundancyEnable OBJECT-TYPE
  SYNTAX INTEGER {
    yes(1),
    no(2)
  }
  ACCESS read-write
  STATUS mandatory
  DESCRIPTION
    "Variable name: L2REDUNDANCY
    WebUi Label: Enable ring/network coupling/dual homing
    Enable Ring/Network Coupling/Dual Homing."
  ::= { mGuardL2Redundancy 1 }

-- L2REDUNDANCY_PORT
mGuardL2RedundancyPort OBJECT-TYPE
  SYNTAX INTEGER {
    intern(1),
    extern(2)
  }
  ACCESS read-write
  STATUS mandatory
  DESCRIPTION
    "Variable name: L2REDUNDANCY_PORT
    WebUi Label: Redundancy port
    Redundancy Port: 'Trusted/Intern' or 'Untrusted/Extern'."
  ::= { mGuardL2Redundancy 2 }

-- L2TP_ENABLED
mGuardVPNL2TPStart OBJECT-TYPE
  SYNTAX INTEGER {
    yes(1),
    no(2)
  }
  ACCESS read-write
  STATUS mandatory
  DESCRIPTION
    "Variable name: L2TP_ENABLED
    WebUi Label: Start L2TP server for IPsec/L2TP
    Start the L2TP Server ? yes,no"
  ::= { mGuardVPNL2TP 1 }

-- L2TP_FROM
mGuardVPNL2TPRemoteIPRangeStart OBJECT-TYPE
  SYNTAX IpAddress
  ACCESS read-write
  STATUS mandatory
  DESCRIPTION
    "Variable name: L2TP_FROM
    WebUi Label: Remote IP range start
    Start of range of remote IPs."
  ::= { mGuardVPNL2TP 3 }

-- L2TP_LOCAL
mGuardVPNL2TPLocalIP OBJECT-TYPE
  SYNTAX IpAddress
  ACCESS read-write
  STATUS mandatory
  DESCRIPTION
    "Variable name: L2TP_LOCAL
    WebUi Label: Local IP for L2TP connections
    Local IP for L2TP connections"
  ::= { mGuardVPNL2TP 2 }


-- L2TP_PPPD_OPTIONS table
mGuardVPNL2TPpppdOptTable OBJECT-TYPE
  SYNTAX SEQUENCE OF MGuardVPNL2TPpppdOptEntry
  ACCESS not-accessible
  STATUS mandatory
  DESCRIPTION
    "A table of L2TP_PPPD_OPTIONS"
  ::= { mGuardVPNL2TP 5 }

-- L2TP_PPPD_OPTIONS table entry
mGuardVPNL2TPpppdOptEntry OBJECT-TYPE
  SYNTAX MGuardVPNL2TPpppdOptEntry
  ACCESS not-accessible
  STATUS mandatory
  DESCRIPTION
    "An entry of L2TP_PPPD_OPTIONS"
  INDEX { mGuardVPNL2TPpppdOptIndex }
  ::= { mGuardVPNL2TPpppdOptTable 1 }

MGuardVPNL2TPpppdOptEntry ::= SEQUENCE {
  mGuardVPNL2TPpppdOptIndex                INTEGER,
  mGuardVPNL2TPpppdOptValue                DisplayString,
  mGuardVPNL2TPpppdOptRowStatus            RowStatus
}

-- L2TP_PPPD_OPTIONS table index
mGuardVPNL2TPpppdOptIndex OBJECT-TYPE
  SYNTAX INTEGER (1..2147483647)
  ACCESS not-accessible
  STATUS mandatory
  DESCRIPTION
    "Index to L2TP_PPPD_OPTIONS"
  ::= { mGuardVPNL2TPpppdOptEntry 1 }

-- L2TP_PPPD_OPTIONS row status
mGuardVPNL2TPpppdOptRowStatus OBJECT-TYPE
  SYNTAX RowStatus
  ACCESS read-write
  STATUS mandatory
  DESCRIPTION
    "RowStatus of L2TP_PPPD_OPTIONS"
  ::= { mGuardVPNL2TPpppdOptEntry 3 }

-- L2TP_PPPD_OPTIONS.OPTION
mGuardVPNL2TPpppdOptValue OBJECT-TYPE
  SYNTAX DisplayString
  ACCESS read-write
  STATUS mandatory
  DESCRIPTION
    "Variable name: L2TP_PPPD_OPTIONS.OPTION
    WebUi Label: Option
    The pppd option."
  ::= { mGuardVPNL2TPpppdOptEntry 2 }

-- L2TP_TO
mGuardVPNL2TPRemoteIPRangeEnd OBJECT-TYPE
  SYNTAX IpAddress
  ACCESS read-write
  STATUS mandatory
  DESCRIPTION
    "Variable name: L2TP_TO
    WebUi Label: Remote IP range end
    End of range of remote IPs."
  ::= { mGuardVPNL2TP 4 }

-- LLDPD_ENABLE
mGuardLLDPAdminStatus OBJECT-TYPE
  SYNTAX INTEGER {
    yes(1),
    no(2)
  }
  ACCESS read-write
  STATUS mandatory
  DESCRIPTION
    "Variable name: LLDPD_ENABLE
    WebUi Label: Enable LLDP
    Enables or disables the LLDP functionality."
  ::= { mGuardLLDP 1 }

-- LLDPD_EXT_MAX_NEIGHBORS
mGuardLLDPExtMaxNeighbors OBJECT-TYPE
  SYNTAX INTEGER(1..50)
  ACCESS read-write
  STATUS mandatory
  DESCRIPTION
    "Variable name: LLDPD_EXT_MAX_NEIGHBORS
    WebUi Label: --
    The maximum number of network neighbors connected to the external
    interface for which LLDP maintains neighbor information."
  ::= { mGuardLLDP 3 }

-- LLDPD_INT_MAX_NEIGHBORS
mGuardLLDPIntMaxNeighbors OBJECT-TYPE
  SYNTAX INTEGER(1..50)
  ACCESS read-write
  STATUS mandatory
  DESCRIPTION
    "Variable name: LLDPD_INT_MAX_NEIGHBORS
    WebUi Label: --
    The maximum number of network neighbors connected to the internal
    interface for which LLDP maintains neighbor information."
  ::= { mGuardLLDP 2 }


-- LOCAL_ALIASES table
mGuardRouterLocalAliasesTable OBJECT-TYPE
  SYNTAX SEQUENCE OF MGuardRouterLocalAliasesEntry
  ACCESS not-accessible
  STATUS mandatory
  DESCRIPTION
    "A table of LOCAL_ALIASES"
  ::= { mGuardRouterLocal 4 }

-- LOCAL_ALIASES table entry
mGuardRouterLocalAliasesEntry OBJECT-TYPE
  SYNTAX MGuardRouterLocalAliasesEntry
  ACCESS not-accessible
  STATUS mandatory
  DESCRIPTION
    "An entry of LOCAL_ALIASES"
  INDEX { mGuardLocalAliasIndex }
  ::= { mGuardRouterLocalAliasesTable 1 }

MGuardRouterLocalAliasesEntry ::= SEQUENCE {
  mGuardLocalAliasIndex                    INTEGER,
  mGuardLocalAliasIpAddress                IpAddress,
  mGuardLocalAliasNetmask                  IpAddress,
  mGuardLocalAliasRowStatus                RowStatus,
  mGuardLocalAliasUseVLAN                  INTEGER,
  mGuardLocalAliasVLANid                   INTEGER,
  mGuardLocalAliasOSPFAreaValue            INTEGER,
  mGuardLocalAliasOSPFAreaRef              OBJECT IDENTIFIER
}

-- LOCAL_ALIASES table index
mGuardLocalAliasIndex OBJECT-TYPE
  SYNTAX INTEGER (1..2147483647)
  ACCESS not-accessible
  STATUS mandatory
  DESCRIPTION
    "Index to LOCAL_ALIASES"
  ::= { mGuardRouterLocalAliasesEntry 1 }

-- LOCAL_ALIASES row status
mGuardLocalAliasRowStatus OBJECT-TYPE
  SYNTAX RowStatus
  ACCESS read-write
  STATUS mandatory
  DESCRIPTION
    "RowStatus of LOCAL_ALIASES"
  ::= { mGuardRouterLocalAliasesEntry 4 }

-- LOCAL_ALIASES.OSPF_AREA_REF
mGuardLocalAliasOSPFAreaValue OBJECT-TYPE
  SYNTAX INTEGER {
    none(1)
  }
  ACCESS read-write
  STATUS mandatory
  DESCRIPTION
    "Variable name: LOCAL_ALIASES.OSPF_AREA_REF
    WebUi Label: OSPF area
    This object is effective if and only if the
    'mGuardLocalAliasOSPFAreaRef' object contains the OID of this object.
    When this object is read, it always returns the value 'none'. When the
    value 'none' is written to this object, no OSPF Area is used."
  ::= { mGuardRouterLocalAliasesEntry 7 }

-- LOCAL_ALIASES.OSPF_AREA_REF reference
mGuardLocalAliasOSPFAreaRef OBJECT-TYPE
  SYNTAX OBJECT IDENTIFIER
  ACCESS read-write
  STATUS mandatory
  DESCRIPTION
    "Variable name: LOCAL_ALIASES.OSPF_AREA_REF
    WebUi Label: OSPF area
    When this object contains the OID of an 'mGuardOSPFAreaIndex' object,
    the corresponding OSPF Area is attached to this alias. To select an
    OSPF Area in this manner, write the OID of the corresponding
    'mGuardOSPFAreaIndex' object to this object. To disable this feature,
    set the 'mGuardLocalAliasOSPFAreaValue' object."
  ::= { mGuardRouterLocalAliasesEntry 8 }

-- LOCAL_ALIASES.USE_VLAN
mGuardLocalAliasUseVLAN OBJECT-TYPE
  SYNTAX INTEGER {
    yes(1),
    no(2)
  }
  ACCESS read-write
  STATUS mandatory
  DESCRIPTION
    "Variable name: LOCAL_ALIASES.USE_VLAN
    WebUi Label: Use VLAN
    Use VLAN tagging with this Alias interface."
  ::= { mGuardRouterLocalAliasesEntry 5 }

-- LOCAL_ALIASES.LOCAL_NET
mGuardLocalAliasNetmask OBJECT-TYPE
  SYNTAX IpAddress
  ACCESS read-write
  STATUS mandatory
  DESCRIPTION
    "Variable name: LOCAL_ALIASES.LOCAL_NET
    WebUi Label: Netmask
    Netmask."
  ::= { mGuardRouterLocalAliasesEntry 3 }

-- LOCAL_ALIASES.VLAN_ID
mGuardLocalAliasVLANid OBJECT-TYPE
  SYNTAX INTEGER(1..4094)
  ACCESS read-write
  STATUS mandatory
  DESCRIPTION
    "Variable name: LOCAL_ALIASES.VLAN_ID
    WebUi Label: VLAN ID
    VLAN ID to be used with this Alias."
  ::= { mGuardRouterLocalAliasesEntry 6 }

-- LOCAL_ALIASES.LOCAL_IP
mGuardLocalAliasIpAddress OBJECT-TYPE
  SYNTAX IpAddress
  ACCESS read-write
  STATUS mandatory
  DESCRIPTION
    "Variable name: LOCAL_ALIASES.LOCAL_IP
    WebUi Label: IP address
    IP address."
  ::= { mGuardRouterLocalAliasesEntry 2 }


-- LOCAL_ROUTES table
mGuardLocalRoutesTable OBJECT-TYPE
  SYNTAX SEQUENCE OF MGuardLocalRoutesEntry
  ACCESS not-accessible
  STATUS mandatory
  DESCRIPTION
    "A table of LOCAL_ROUTES"
  ::= { mGuardRouterLocal 5 }

-- LOCAL_ROUTES table entry
mGuardLocalRoutesEntry OBJECT-TYPE
  SYNTAX MGuardLocalRoutesEntry
  ACCESS not-accessible
  STATUS mandatory
  DESCRIPTION
    "An entry of LOCAL_ROUTES"
  INDEX { mGuardLocalRouteIndex }
  ::= { mGuardLocalRoutesTable 1 }

MGuardLocalRoutesEntry ::= SEQUENCE {
  mGuardLocalRouteIndex                    INTEGER,
  mGuardLocalRouteNetwork                  DisplayString,
  mGuardLocalRouteGateway                  IpAddress,
  mGuardLocalRouteRowStatus                RowStatus
}

-- LOCAL_ROUTES table index
mGuardLocalRouteIndex OBJECT-TYPE
  SYNTAX INTEGER (1..2147483647)
  ACCESS not-accessible
  STATUS mandatory
  DESCRIPTION
    "Index to LOCAL_ROUTES"
  ::= { mGuardLocalRoutesEntry 1 }

-- LOCAL_ROUTES row status
mGuardLocalRouteRowStatus OBJECT-TYPE
  SYNTAX RowStatus
  ACCESS read-write
  STATUS mandatory
  DESCRIPTION
    "RowStatus of LOCAL_ROUTES"
  ::= { mGuardLocalRoutesEntry 4 }

-- LOCAL_ROUTES.GATEWAY
mGuardLocalRouteGateway OBJECT-TYPE
  SYNTAX IpAddress
  ACCESS read-write
  STATUS mandatory
  DESCRIPTION
    "Variable name: LOCAL_ROUTES.GATEWAY
    WebUi Label: Gateway
    Routing gateway."
  ::= { mGuardLocalRoutesEntry 3 }

-- LOCAL_ROUTES.NETWORK
mGuardLocalRouteNetwork OBJECT-TYPE
  SYNTAX DisplayString
  ACCESS read-write
  STATUS mandatory
  DESCRIPTION
    "Variable name: LOCAL_ROUTES.NETWORK
    WebUi Label: Network
    Routed network."
  ::= { mGuardLocalRoutesEntry 2 }

-- LOGGING_UDP_ENABLE
mGuardLoggingRemoteActivate OBJECT-TYPE
  SYNTAX INTEGER {
    yes(1),
    no(2)
  }
  ACCESS read-write
  STATUS mandatory
  DESCRIPTION
    "Variable name: LOGGING_UDP_ENABLE
    WebUi Label: Activate remote UDP logging
    Activate remote logging?"
  ::= { mGuardLogging 1 }

-- LOGGING_UDP_SERVER_IP
mGuardLoggingRemoteIP OBJECT-TYPE
  SYNTAX IpAddress
  ACCESS read-write
  STATUS mandatory
  DESCRIPTION
    "Variable name: LOGGING_UDP_SERVER_IP
    WebUi Label: Log server IP address
    IP address of the remote log server"
  ::= { mGuardLogging 2 }

-- LOGGING_UDP_SERVER_PORT
mGuardLoggingRemotePort OBJECT-TYPE
  SYNTAX INTEGER(1..65535)
  ACCESS read-write
  STATUS mandatory
  DESCRIPTION
    "Variable name: LOGGING_UDP_SERVER_PORT
    WebUi Label: Log server port (normally 514)
    UDP port of the remote logging service"
  ::= { mGuardLogging 4 }

-- LOG_DEFAULT_INCOMING
mGuardFirewallINLogDefault OBJECT-TYPE
  SYNTAX INTEGER {
    yes(1),
    no(2)
  }
  ACCESS read-write
  STATUS mandatory
  DESCRIPTION
    "Variable name: LOG_DEFAULT_INCOMING
    WebUi Label: Log entries for unknown connection attempts
    Log entries for unknown connection attempts"
  ::= { mGuardFirewallIncoming 2 }

-- LOG_DEFAULT_INCOMING_DMZ_LAN
mGuardFirewallDLINLogDefault OBJECT-TYPE
  SYNTAX INTEGER {
    yes(1),
    no(2)
  }
  ACCESS read-write
  STATUS mandatory
  DESCRIPTION
    "Variable name: LOG_DEFAULT_INCOMING_DMZ_LAN
    WebUi Label: Log entries for unknown connection attempts
    Log entries for unknown connection attempts"
  ::= { mGuardFirewallIncomingDmzLan 2 }

-- LOG_DEFAULT_INCOMING_WAN_DMZ
mGuardFirewallWDINLogDefault OBJECT-TYPE
  SYNTAX INTEGER {
    yes(1),
    no(2)
  }
  ACCESS read-write
  STATUS mandatory
  DESCRIPTION
    "Variable name: LOG_DEFAULT_INCOMING_WAN_DMZ
    WebUi Label: Log entries for unknown connection attempts
    Log entries for unknown connection attempts"
  ::= { mGuardFirewallIncomingWanDmz 2 }

-- LOG_DEFAULT_OUTGOING
mGuardFirewallOUTLogDefault OBJECT-TYPE
  SYNTAX INTEGER {
    yes(1),
    no(2)
  }
  ACCESS read-write
  STATUS mandatory
  DESCRIPTION
    "Variable name: LOG_DEFAULT_OUTGOING
    WebUi Label: Log entries for unknown connection attempts
    Log entries for unknown connection attempts"
  ::= { mGuardFirewallOutgoing 2 }

-- LOG_DEFAULT_OUTGOING_DMZ_WAN
mGuardFirewallDWOUTLogDefault OBJECT-TYPE
  SYNTAX INTEGER {
    yes(1),
    no(2)
  }
  ACCESS read-write
  STATUS mandatory
  DESCRIPTION
    "Variable name: LOG_DEFAULT_OUTGOING_DMZ_WAN
    WebUi Label: Log entries for unknown connection attempts
    Log entries for unknown connection attempts"
  ::= { mGuardFirewallOutgoingDmzWan 2 }

-- LOG_DEFAULT_OUTGOING_LAN_DMZ
mGuardFirewallLDOUTLogDefault OBJECT-TYPE
  SYNTAX INTEGER {
    yes(1),
    no(2)
  }
  ACCESS read-write
  STATUS mandatory
  DESCRIPTION
    "Variable name: LOG_DEFAULT_OUTGOING_LAN_DMZ
    WebUi Label: Log entries for unknown connection attempts
    Log entries for unknown connection attempts"
  ::= { mGuardFirewallOutgoingLanDmz 2 }

-- MOBILE_PASSWORD
mGuardMobilePassword OBJECT-TYPE
  SYNTAX DisplayString
  ACCESS read-write
  STATUS mandatory
  DESCRIPTION
    "Variable name: MOBILE_PASSWORD
    WebUi Label: Mobile password
    Changes the password for the user 'mobile', whose only allowed action
    is sending text messages."
  ::= { mGuardPasswords 7 }


-- MODBUS_RULESETS table
mGuardFWModbusRulesetTable OBJECT-TYPE
  SYNTAX SEQUENCE OF MGuardFWModbusRulesetEntry
  ACCESS not-accessible
  STATUS mandatory
  DESCRIPTION
    "A table of MODBUS_RULESETS"
  ::= { mGuardFirewallModbus 1 }

-- MODBUS_RULESETS table entry
mGuardFWModbusRulesetEntry OBJECT-TYPE
  SYNTAX MGuardFWModbusRulesetEntry
  ACCESS not-accessible
  STATUS mandatory
  DESCRIPTION
    "An entry of MODBUS_RULESETS"
  INDEX { mGuardFWModbusRulesetIndex }
  ::= { mGuardFWModbusRulesetTable 1 }

MGuardFWModbusRulesetEntry ::= SEQUENCE {
  mGuardFWModbusRulesetIndex               INTEGER,
  mGuardFWModbusRulesetRowStatus           RowStatus,
  mGuardFWModbusRulesetName                DisplayString,
  mGuardFWModbusRulesetLogDef              INTEGER
}

-- MODBUS_RULESETS table index
mGuardFWModbusRulesetIndex OBJECT-TYPE
  SYNTAX INTEGER (1..2147483647)
  ACCESS not-accessible
  STATUS mandatory
  DESCRIPTION
    "Index to MODBUS_RULESETS"
  ::= { mGuardFWModbusRulesetEntry 1 }

-- MODBUS_RULESETS row status
mGuardFWModbusRulesetRowStatus OBJECT-TYPE
  SYNTAX RowStatus
  ACCESS read-write
  STATUS mandatory
  DESCRIPTION
    "RowStatus of MODBUS_RULESETS"
  ::= { mGuardFWModbusRulesetEntry 2 }


-- MODBUS_RULESETS.SET table
mGuardFWModbusRuleTable OBJECT-TYPE
  SYNTAX SEQUENCE OF MGuardFWModbusRuleEntry
  ACCESS not-accessible
  STATUS mandatory
  DESCRIPTION
    "A table of MODBUS_RULESETS.SET"
  ::= { mGuardFirewallModbus 2 }

-- MODBUS_RULESETS.SET table entry
mGuardFWModbusRuleEntry OBJECT-TYPE
  SYNTAX MGuardFWModbusRuleEntry
  ACCESS not-accessible
  STATUS mandatory
  DESCRIPTION
    "An entry of MODBUS_RULESETS.SET"
  INDEX { mGuardFWModbusRulesetIndex, mGuardFWModbusRuleIndex }
  ::= { mGuardFWModbusRuleTable 1 }

MGuardFWModbusRuleEntry ::= SEQUENCE {
  mGuardFWModbusRuleIndex                  INTEGER,
  mGuardFWModbusRuleRowStatus              RowStatus,
  mGuardFWModbusRuleAddrRange              DisplayString,
  mGuardFWModbusRuleComment                DisplayString,
  mGuardFWModbusRuleLog                    INTEGER,
  mGuardFWModbusRuleFunctionCode           DisplayString,
  mGuardFWModbusRuleTarget                 INTEGER
}

-- MODBUS_RULESETS.SET table index
mGuardFWModbusRuleIndex OBJECT-TYPE
  SYNTAX INTEGER (1..2147483647)
  ACCESS not-accessible
  STATUS mandatory
  DESCRIPTION
    "Index to MODBUS_RULESETS.SET"
  ::= { mGuardFWModbusRuleEntry 1 }

-- MODBUS_RULESETS.SET row status
mGuardFWModbusRuleRowStatus OBJECT-TYPE
  SYNTAX RowStatus
  ACCESS read-write
  STATUS mandatory
  DESCRIPTION
    "RowStatus of MODBUS_RULESETS.SET"
  ::= { mGuardFWModbusRuleEntry 2 }

-- MODBUS_RULESETS.SET.COMMENT
mGuardFWModbusRuleComment OBJECT-TYPE
  SYNTAX DisplayString
  ACCESS read-write
  STATUS mandatory
  DESCRIPTION
    "Variable name: MODBUS_RULESETS.SET.COMMENT
    WebUi Label: Comment
    A comment."
  ::= { mGuardFWModbusRuleEntry 4 }

-- MODBUS_RULESETS.SET.MODBUS_FUNCTION_CODE
mGuardFWModbusRuleFunctionCode OBJECT-TYPE
  SYNTAX DisplayString
  ACCESS read-write
  STATUS mandatory
  DESCRIPTION
    "Variable name: MODBUS_RULESETS.SET.MODBUS_FUNCTION_CODE
    WebUi Label: Function code
    A numeric function code (i.e. a number between 1 and 255) or the word
    'any'."
  ::= { mGuardFWModbusRuleEntry 6 }

-- MODBUS_RULESETS.SET.ADDRESS_RANGE
mGuardFWModbusRuleAddrRange OBJECT-TYPE
  SYNTAX DisplayString
  ACCESS read-write
  STATUS mandatory
  DESCRIPTION
    "Variable name: MODBUS_RULESETS.SET.ADDRESS_RANGE
    WebUi Label: PDU addresses
    A PDU address (i.e. a number between 0 and 65535), address range (i.e.
    two numbers separated by a colon), or the word 'any'."
  ::= { mGuardFWModbusRuleEntry 3 }

-- MODBUS_RULESETS.SET.LOG
mGuardFWModbusRuleLog OBJECT-TYPE
  SYNTAX INTEGER {
    yes(1),
    no(2)
  }
  ACCESS read-write
  STATUS mandatory
  DESCRIPTION
    "Variable name: MODBUS_RULESETS.SET.LOG
    WebUi Label: Log
    Log entries for matching packets."
  ::= { mGuardFWModbusRuleEntry 5 }

-- MODBUS_RULESETS.SET.TARGET
mGuardFWModbusRuleTarget OBJECT-TYPE
  SYNTAX INTEGER {
    accept(1),
    drop(3)
  }
  ACCESS read-write
  STATUS mandatory
  DESCRIPTION
    "Variable name: MODBUS_RULESETS.SET.TARGET
    WebUi Label: Action
    The target (i.e. what to do with mathching packets)."
  ::= { mGuardFWModbusRuleEntry 7 }

-- MODBUS_RULESETS.LOG_DEFAULT
mGuardFWModbusRulesetLogDef OBJECT-TYPE
  SYNTAX INTEGER {
    yes(1),
    no(2)
  }
  ACCESS read-write
  STATUS mandatory
  DESCRIPTION
    "Variable name: MODBUS_RULESETS.LOG_DEFAULT
    WebUi Label: Log entries for unknown packets
    Log entries for unknown packets."
  ::= { mGuardFWModbusRulesetEntry 4 }

-- MODBUS_RULESETS.FRIENDLY_NAME
mGuardFWModbusRulesetName OBJECT-TYPE
  SYNTAX DisplayString
  ACCESS read-write
  STATUS mandatory
  DESCRIPTION
    "Variable name: MODBUS_RULESETS.FRIENDLY_NAME
    WebUi Label: Name
    A name identifying the Modbus rule set."
  ::= { mGuardFWModbusRulesetEntry 3 }

-- MODEM_ANALOG_COUNTRY
mGuardModemCountry OBJECT-TYPE
  SYNTAX INTEGER {
    ar(1),
    at(2),
    au(3),
    be(4),
    bg(5),
    br(6),
    ca(7),
    ch(8),
    cl(9),
    cn(10),
    cy(11),
    cz(12),
    de(13),
    dk(14),
    ee(15),
    es(16),
    fi(17),
    fr(18),
    gb(19),
    gr(20),
    hk(21),
    hu(22),
    id(23),
    ie(24),
    il(25),
    in(26),
    is(27),
    it(28),
    jp(29),
    kr(30),
    li(31),
    lt(32),
    lu(33),
    lv(34),
    mt(35),
    mx(36),
    my(37),
    nl(38),
    no(39),
    nz(40),
    ph(41),
    pl(42),
    pt(43),
    ro(44),
    ru(45),
    se(46),
    sg(47),
    si(48),
    sk(49),
    th(50),
    tr(51),
    tw(52),
    us(53),
    za(54)
  }
  ACCESS read-write
  STATUS mandatory
  DESCRIPTION
    "Variable name: MODEM_ANALOG_COUNTRY
    WebUi Label: Country
    Country defining electrical compliance with telco line"
  ::= { mGuardModem 19 }

-- MODEM_ANALOG_EXTLINE
mGuardModemExtLine OBJECT-TYPE
  SYNTAX INTEGER {
    yes(1),
    no(2)
  }
  ACCESS read-write
  STATUS mandatory
  DESCRIPTION
    "Variable name: MODEM_ANALOG_EXTLINE
    WebUi Label: Extension line (regarding dial tone)
    Modem is on an extension line regarding dial tone"
  ::= { mGuardModem 20 }

-- MODEM_ANALOG_SPKRCTRL
mGuardModemAnalogSpeakerCtl OBJECT-TYPE
  SYNTAX INTEGER {
    alwaysOff(10),
    duringEstablishment(11),
    alwaysOn(12),
    afterDialing(13)
  }
  ACCESS read-write
  STATUS mandatory
  DESCRIPTION
    "Variable name: MODEM_ANALOG_SPKRCTRL
    WebUi Label: Speaker control (built-in speaker)
    Modem loudspeaker control"
  ::= { mGuardModem 22 }

-- MODEM_ANALOG_VOLUME
mGuardModemAnalogSpeakerVol OBJECT-TYPE
  SYNTAX INTEGER {
    quiet(10),
    low(11),
    medium(12),
    high(13)
  }
  ACCESS read-write
  STATUS mandatory
  DESCRIPTION
    "Variable name: MODEM_ANALOG_VOLUME
    WebUi Label: Speaker volume (built-in speaker)
    Modem loudspeaker volume"
  ::= { mGuardModem 21 }

-- MODEM_AUTH
mGuardModemAuth OBJECT-TYPE
  SYNTAX INTEGER {
    none(1),
    pap(2),
    chap(3)
  }
  ACCESS read-write
  STATUS mandatory
  DESCRIPTION
    "Variable name: MODEM_AUTH
    WebUi Label: Authentication
    Method to be used to authenticate with the remote peer."
  ::= { mGuardModem 11 }

-- MODEM_BAUDRATE
mGuardModemBaud OBJECT-TYPE
  SYNTAX INTEGER
  ACCESS read-write
  STATUS mandatory
  DESCRIPTION
    "Variable name: MODEM_BAUDRATE
    WebUi Label: Baud rate
    Baud rate of the modem connection."
  ::= { mGuardModem 1 }

-- MODEM_CHAP_LOCAL_NAME
mGuardModemCHAPLocalUser OBJECT-TYPE
  SYNTAX DisplayString
  ACCESS read-write
  STATUS mandatory
  DESCRIPTION
    "Variable name: MODEM_CHAP_LOCAL_NAME
    WebUi Label: Local name
    User name to authenticate at the remote PPP peer via CHAP."
  ::= { mGuardModemCHAP 1 }

-- MODEM_CHAP_REMOTE_NAME
mGuardModemCHAPRemoteUser OBJECT-TYPE
  SYNTAX DisplayString
  ACCESS read-write
  STATUS mandatory
  DESCRIPTION
    "Variable name: MODEM_CHAP_REMOTE_NAME
    WebUi Label: Remote name
    The username to be used by the remote peer to authenticate itself via
    CHAP."
  ::= { mGuardModemCHAP 4 }

-- MODEM_CHAP_REQUIRE_SERVER_AUTH
mGuardModemCHAPRemoteAuth OBJECT-TYPE
  SYNTAX INTEGER {
    yes(1),
    no(2)
  }
  ACCESS read-write
  STATUS mandatory
  DESCRIPTION
    "Variable name: MODEM_CHAP_REQUIRE_SERVER_AUTH
    WebUi Label: CHAP server authentication
    When set to 'yes', require the remote peer to authenticate itself via
    CHAP."
  ::= { mGuardModemCHAP 3 }

-- MODEM_CHAP_SECRET
mGuardModemCHAPLocalPassword OBJECT-TYPE
  SYNTAX DisplayString
  ACCESS read-write
  STATUS mandatory
  DESCRIPTION
    "Variable name: MODEM_CHAP_SECRET
    WebUi Label: Password for client authentication
    Password to authenticate at the remote PPP peer via CHAP."
  ::= { mGuardModemCHAP 2 }

-- MODEM_CHAP_SERVER_SECRET
mGuardModemCHAPRemotePassword OBJECT-TYPE
  SYNTAX DisplayString
  ACCESS read-write
  STATUS mandatory
  DESCRIPTION
    "Variable name: MODEM_CHAP_SERVER_SECRET
    WebUi Label: Password for server authentication
    The password to be used by the remote peer to authenticate itself via
    CHAP."
  ::= { mGuardModemCHAP 5 }

-- MODEM_CRTSCTS
mGuardModemHWHandshakeEnable OBJECT-TYPE
  SYNTAX INTEGER {
    enabled(1),
    disabled(2)
  }
  ACCESS read-write
  STATUS mandatory
  DESCRIPTION
    "Variable name: MODEM_CRTSCTS
    WebUi Label: Hardware handshake RTS/CTS
    Enable hardware handshake"
  ::= { mGuardModem 14 }

-- MODEM_DEBUG
mGuardModemDebug OBJECT-TYPE
  SYNTAX INTEGER {
    yes(1),
    no(2)
  }
  ACCESS read-write
  STATUS mandatory
  DESCRIPTION
    "Variable name: MODEM_DEBUG
    WebUi Label: Verbose modem logging
    Enable Modem (PPP, chat) debugging during dial-out."
  ::= { mGuardModem 24 }

-- MODEM_DOD
mGuardModemDialOnDemand OBJECT-TYPE
  SYNTAX INTEGER {
    yes(1),
    no(2)
  }
  ACCESS read-write
  STATUS mandatory
  DESCRIPTION
    "Variable name: MODEM_DOD
    WebUi Label: Dial on demand
    Establish modem connection on demand."
  ::= { mGuardModem 5 }

-- MODEM_IDLE_TIMEOUT
mGuardModemIdleTimeoutEnabled OBJECT-TYPE
  SYNTAX INTEGER {
    yes(1),
    no(2)
  }
  ACCESS read-write
  STATUS mandatory
  DESCRIPTION
    "Variable name: MODEM_IDLE_TIMEOUT
    WebUi Label: Idle timeout
    Hang up modem connection after being idle."
  ::= { mGuardModem 6 }

-- MODEM_IDLE_TIMEOUT_SECONDS
mGuardModemIdleTimeout OBJECT-TYPE
  SYNTAX INTEGER(1..10000)
  ACCESS read-write
  STATUS mandatory
  DESCRIPTION
    "Variable name: MODEM_IDLE_TIMEOUT_SECONDS
    WebUi Label: Idle time
    The modem idle timeout in seconds."
  ::= { mGuardModem 7 }

-- MODEM_ISDN_L2PROTO
mGuardModemISDNL2Protocol OBJECT-TYPE
  SYNTAX INTEGER {
    mlppp(9)
  }
  ACCESS read-write
  STATUS mandatory
  DESCRIPTION
    "Variable name: MODEM_ISDN_L2PROTO
    WebUi Label: Layer-2 protocol
    ISDN L2 protocol spoken"
  ::= { mGuardModem 18 }

-- MODEM_ISDN_MSN1
mGuardModemISDNMSN1 OBJECT-TYPE
  SYNTAX DisplayString
  ACCESS read-write
  STATUS mandatory
  DESCRIPTION
    "Variable name: MODEM_ISDN_MSN1
    WebUi Label: 1st MSN
    The first MSN"
  ::= { mGuardModem 15 }

-- MODEM_ISDN_MSN2
mGuardModemISDNMSN2 OBJECT-TYPE
  SYNTAX DisplayString
  ACCESS read-write
  STATUS mandatory
  DESCRIPTION
    "Variable name: MODEM_ISDN_MSN2
    WebUi Label: 2nd MSN
    The second MSN"
  ::= { mGuardModem 16 }

-- MODEM_ISDN_PROTOCOL
mGuardModemISDNProtocol OBJECT-TYPE
  SYNTAX INTEGER {
    att5ess(10),
    northerntelecomdms100(11),
    euroISDNnet3(12),
    ins64(14),
    usni1(15),
    vn4(16)
  }
  ACCESS read-write
  STATUS mandatory
  DESCRIPTION
    "Variable name: MODEM_ISDN_PROTOCOL
    WebUi Label: ISDN protocol
    ISDN protocol spoken"
  ::= { mGuardModem 17 }

-- MODEM_LOCAL_IP
mGuardModemLocalIP OBJECT-TYPE
  SYNTAX IpAddress
  ACCESS read-write
  STATUS mandatory
  DESCRIPTION
    "Variable name: MODEM_LOCAL_IP
    WebUi Label: Local IP
    The local IP address for the modem connection. 0.0.0.0 means to accept
    the IP address provided by the remote peer."
  ::= { mGuardModem 8 }

-- MODEM_NETMASK
mGuardModemNetMask OBJECT-TYPE
  SYNTAX IpAddress
  ACCESS read-write
  STATUS mandatory
  DESCRIPTION
    "Variable name: MODEM_NETMASK
    WebUi Label: Netmask
    Set the interface netmask. The value is ORed with the default netmask.
    The default netmask is chosen based on the negotiated remote IP
    address; it is the appropriate network mask for the class of the
    remote IP address, ORed with the netmasks for any non point-to-point
    network interfaces in the system which are on the same network. The
    default is 0.0.0.0."
  ::= { mGuardModem 10 }

-- MODEM_PAP_PASS
mGuardModemPAPLocalPassword OBJECT-TYPE
  SYNTAX DisplayString
  ACCESS read-write
  STATUS mandatory
  DESCRIPTION
    "Variable name: MODEM_PAP_PASS
    WebUi Label: Password
    Password to authenticate at the remote PPP peer via PAP."
  ::= { mGuardModemPAP 2 }

-- MODEM_PAP_REQUIRE_SERVER_AUTH
mGuardModemPAPRemoteAuth OBJECT-TYPE
  SYNTAX INTEGER {
    yes(1),
    no(2)
  }
  ACCESS read-write
  STATUS mandatory
  DESCRIPTION
    "Variable name: MODEM_PAP_REQUIRE_SERVER_AUTH
    WebUi Label: PAP server authentication
    When set to 'yes', require the remote peer to authenticate itself via
    PAP."
  ::= { mGuardModemPAP 3 }

-- MODEM_PAP_SERVER_PASS
mGuardModemPAPRemotePassword OBJECT-TYPE
  SYNTAX DisplayString
  ACCESS read-write
  STATUS mandatory
  DESCRIPTION
    "Variable name: MODEM_PAP_SERVER_PASS
    WebUi Label: Server password
    The password to be used by the remote peer to authenticate itself via
    PAP."
  ::= { mGuardModemPAP 5 }

-- MODEM_PAP_SERVER_USER
mGuardModemPAPRemoteUser OBJECT-TYPE
  SYNTAX DisplayString
  ACCESS read-write
  STATUS mandatory
  DESCRIPTION
    "Variable name: MODEM_PAP_SERVER_USER
    WebUi Label: Server user name
    The username to be used by the remote peer to authenticate itself via
    PAP."
  ::= { mGuardModemPAP 4 }

-- MODEM_PAP_USER
mGuardModemPAPLocalUser OBJECT-TYPE
  SYNTAX DisplayString
  ACCESS read-write
  STATUS mandatory
  DESCRIPTION
    "Variable name: MODEM_PAP_USER
    WebUi Label: User name
    User name to authenticate at the remote PPP peer via PAP."
  ::= { mGuardModemPAP 1 }

-- MODEM_PHONE
mGuardModemPhoneNumber OBJECT-TYPE
  SYNTAX DisplayString
  ACCESS read-write
  STATUS mandatory
  DESCRIPTION
    "Variable name: MODEM_PHONE
    WebUi Label: Phone number to call
    The phone number to be dialed to establish the modem connection."
  ::= { mGuardModem 4 }

-- MODEM_REMOTE_IP
mGuardModemRemoteIP OBJECT-TYPE
  SYNTAX IpAddress
  ACCESS read-write
  STATUS mandatory
  DESCRIPTION
    "Variable name: MODEM_REMOTE_IP
    WebUi Label: Remote IP
    The remote IP address for the modem connection. 0.0.0.0 means to
    accept the IP address provided by the remote peer."
  ::= { mGuardModem 9 }

-- MODEM_RESET_STRING
mGuardModemResetString OBJECT-TYPE
  SYNTAX DisplayString
  ACCESS read-write
  STATUS mandatory
  DESCRIPTION
    "Variable name: MODEM_RESET_STRING
    WebUi Label: Modem init string
    The chat script reset string. The default is: '' +++ATH"
  ::= { mGuardModem 3 }

-- MY_DMZ_DEV_MTU
mGuardRouterDmzDevMTU OBJECT-TYPE
  SYNTAX INTEGER(46..1500)
  ACCESS read-write
  STATUS mandatory
  DESCRIPTION
    "Variable name: MY_DMZ_DEV_MTU
    WebUi Label: MTU of the DMZ interface
    Set the MTU for the DMZ interface. Router-Mode only."
  ::= { mGuardRouterDmz 3 }

-- MY_LOCAL_DEV_MTU
mGuardRouterLocalDevMTU OBJECT-TYPE
  SYNTAX INTEGER(46..1500)
  ACCESS read-write
  STATUS mandatory
  DESCRIPTION
    "Variable name: MY_LOCAL_DEV_MTU
    WebUi Label: MTU of the internal interface
    Set the MTU for the local interface. Router-Mode only."
  ::= { mGuardRouterLocal 6 }

-- MY_LOCAL_DEV_VLAN_MTU
mGuardRouterLocalDevVlanMTU OBJECT-TYPE
  SYNTAX INTEGER(46..1500)
  ACCESS read-write
  STATUS mandatory
  DESCRIPTION
    "Variable name: MY_LOCAL_DEV_VLAN_MTU
    WebUi Label: MTU of the internal interface for VLAN
    Set the MTU for the VLAN if enabled on local interface. Router-Mode
    only."
  ::= { mGuardRouterLocal 9 }

-- MY_LOCAL_IP
mGuardRouterLocalIP OBJECT-TYPE
  SYNTAX IpAddress
  ACCESS read-write
  STATUS mandatory
  DESCRIPTION
    "Variable name: MY_LOCAL_IP
    WebUi Label: --
    The internal IP address of this device in router mode."
  ::= { mGuardRouterLocal 1 }

-- MY_LOCAL_NET
mGuardRouterLocalNetmask OBJECT-TYPE
  SYNTAX IpAddress
  ACCESS read-write
  STATUS mandatory
  DESCRIPTION
    "Variable name: MY_LOCAL_NET
    WebUi Label: --
    The internal subnet mask of this device in router mode."
  ::= { mGuardRouterLocal 2 }

-- MY_LOCAL_OSPF_AREA_REF
mGuardRouterLocalOSPFAreaValue OBJECT-TYPE
  SYNTAX INTEGER {
    none(1)
  }
  ACCESS read-write
  STATUS mandatory
  DESCRIPTION
    "Variable name: MY_LOCAL_OSPF_AREA_REF
    WebUi Label: --
    This object is effective if and only if the
    'mGuardRouterLocalOSPFAreaRef' object contains the OID of this object.
    When this object is read, it always returns the value 'none'. When the
    value 'none' is written to this object, no OSPF Area is used."
  ::= { mGuardRouterLocal 12 }

-- MY_LOCAL_OSPF_AREA_REF reference
mGuardRouterLocalOSPFAreaRef OBJECT-TYPE
  SYNTAX OBJECT IDENTIFIER
  ACCESS read-write
  STATUS mandatory
  DESCRIPTION
    "Variable name: MY_LOCAL_OSPF_AREA_REF
    WebUi Label: --
    When this object contains the OID of an 'mGuardOSPFAreaIndex' object,
    the corresponding OSPF Area is attached to this network. To select an
    OSPF Area in this manner, write the OID of the corresponding
    'mGuardOSPFAreaIndex' object to this object. To disable this feature,
    set the 'mGuardRouterLocalOSPFAreaValue' object."
  ::= { mGuardRouterLocal 13 }

-- MY_LOCAL_USE_VLAN
mGuardRouterLocalUseVLAN OBJECT-TYPE
  SYNTAX INTEGER {
    yes(1),
    no(2)
  }
  ACCESS read-write
  STATUS mandatory
  DESCRIPTION
    "Variable name: MY_LOCAL_USE_VLAN
    WebUi Label: --
    Use VLAN for the local interface. Router-Mode only."
  ::= { mGuardRouterLocal 7 }

-- MY_LOCAL_VLAN_ID
mGuardRouterLocalVlanId OBJECT-TYPE
  SYNTAX INTEGER(1..4094)
  ACCESS read-write
  STATUS mandatory
  DESCRIPTION
    "Variable name: MY_LOCAL_VLAN_ID
    WebUi Label: --
    VLAN-ID for the local interface, used only if set to use VLAN. Router-
    Mode only."
  ::= { mGuardRouterLocal 8 }

-- MY_ROUTER_DEV_MAC
mGuardRouterExternDevMAC OBJECT-TYPE
  SYNTAX MacAddress
  ACCESS read-write
  STATUS mandatory
  DESCRIPTION
    "Variable name: MY_ROUTER_DEV_MAC
    WebUi Label: MAC for external interface
    A unicast MAC address for the external interface or zero MAC if not
    used."
  ::= { mGuardRouterExtern 10 }

-- MY_ROUTER_DEV_MAC_MANUAL
mGuardRouterExternDevMACMan OBJECT-TYPE
  SYNTAX INTEGER {
    yes(1),
    no(2)
  }
  ACCESS read-write
  STATUS mandatory
  DESCRIPTION
    "Variable name: MY_ROUTER_DEV_MAC_MANUAL
    WebUi Label: Use manually configured MAC address
    Use manually provided MAC address instead of factory provided MAC."
  ::= { mGuardRouterExtern 11 }

-- MY_ROUTER_DEV_MTU
mGuardRouterExternDevMTU OBJECT-TYPE
  SYNTAX INTEGER(46..1500)
  ACCESS read-write
  STATUS mandatory
  DESCRIPTION
    "Variable name: MY_ROUTER_DEV_MTU
    WebUi Label: MTU of the external interface
    Set the MTU for the external interface. Router-Mode only."
  ::= { mGuardRouterExtern 6 }

-- MY_ROUTER_DEV_VLAN_MTU
mGuardRouterExternDevVlanMTU OBJECT-TYPE
  SYNTAX INTEGER(46..1500)
  ACCESS read-write
  STATUS mandatory
  DESCRIPTION
    "Variable name: MY_ROUTER_DEV_VLAN_MTU
    WebUi Label: MTU of the external interface for VLAN
    Set the MTU for the VLAN if enabled on external interface. Router-Mode
    only."
  ::= { mGuardRouterExtern 9 }

-- MY_ROUTER_IP
mGuardRouterExternStaticIP OBJECT-TYPE
  SYNTAX IpAddress
  ACCESS read-write
  STATUS mandatory
  DESCRIPTION
    "Variable name: MY_ROUTER_IP
    WebUi Label: --
    The external IP address of this device in router mode (when statically
    configured)."
  ::= { mGuardRouterExternStatic 1 }

-- MY_ROUTER_NET
mGuardRouterExternStaticNetmask OBJECT-TYPE
  SYNTAX IpAddress
  ACCESS read-write
  STATUS mandatory
  DESCRIPTION
    "Variable name: MY_ROUTER_NET
    WebUi Label: --
    The external netmask of this device in router mode (when statically
    configured)."
  ::= { mGuardRouterExternStatic 2 }

-- MY_ROUTER_OSPF_AREA_REF
mGuardRouterExternOSPFAreaValue OBJECT-TYPE
  SYNTAX INTEGER {
    none(1)
  }
  ACCESS read-write
  STATUS mandatory
  DESCRIPTION
    "Variable name: MY_ROUTER_OSPF_AREA_REF
    WebUi Label: --
    This object is effective if and only if the
    'mGuardRouterExternOSPFAreaRef' object contains the OID of this
    object. When this object is read, it always returns the value 'none'.
    When the value 'none' is written to this object, no OSPF Area is used."
  ::= { mGuardRouterExtern 12 }

-- MY_ROUTER_OSPF_AREA_REF reference
mGuardRouterExternOSPFAreaRef OBJECT-TYPE
  SYNTAX OBJECT IDENTIFIER
  ACCESS read-write
  STATUS mandatory
  DESCRIPTION
    "Variable name: MY_ROUTER_OSPF_AREA_REF
    WebUi Label: --
    When this object contains the OID of an 'mGuardOSPFAreaIndex' object,
    the corresponding OSPF Area is attached to this network. To select an
    OSPF Area in this manner, write the OID of the corresponding
    'mGuardOSPFAreaIndex' object to this object. To disable this feature,
    set the 'mGuardRouterExternOSPFAreaValue' object."
  ::= { mGuardRouterExtern 13 }

-- MY_ROUTER_USE_VLAN
mGuardRouterExternUseVLAN OBJECT-TYPE
  SYNTAX INTEGER {
    yes(1),
    no(2)
  }
  ACCESS read-write
  STATUS mandatory
  DESCRIPTION
    "Variable name: MY_ROUTER_USE_VLAN
    WebUi Label: --
    Use VLAN for the external interface. Router-Mode only."
  ::= { mGuardRouterExtern 7 }

-- MY_ROUTER_VLAN_ID
mGuardRouterExternVlanId OBJECT-TYPE
  SYNTAX INTEGER(1..4094)
  ACCESS read-write
  STATUS mandatory
  DESCRIPTION
    "Variable name: MY_ROUTER_VLAN_ID
    WebUi Label: --
    VLAN-ID for the external interface, used only if set to use VLAN.
    Router-Mode only."
  ::= { mGuardRouterExtern 8 }

-- NETADMIN_PASSWORD
mGuardNetadminPassword OBJECT-TYPE
  SYNTAX DisplayString
  ACCESS read-write
  STATUS mandatory
  DESCRIPTION
    "Variable name: NETADMIN_PASSWORD
    WebUi Label: --
    Changes the password for the user 'netadmin', who can view the systems
    configuration and modify parts of the configuration when the
    appropriate access right have been given by user 'admin' or 'root'."
  ::= { mGuardPasswords 5 }

-- NETADMIN_SHELL_ENABLE
mGuardSSHNetadminEnable OBJECT-TYPE
  SYNTAX INTEGER {
    yes(1),
    no(2)
  }
  ACCESS read-write
  STATUS mandatory
  DESCRIPTION
    "Variable name: NETADMIN_SHELL_ENABLE
    WebUi Label: --
    Enable SSH Access for user 'netadmin'."
  ::= { mGuardSSHRemoteAccess 7 }

-- NETWORKMODE
mGuardNetworkModeType OBJECT-TYPE
  SYNTAX INTEGER {
    stealth(1),
    router(2)
  }
  ACCESS read-write
  STATUS mandatory
  DESCRIPTION
    "Variable name: NETWORKMODE
    WebUi Label: Network mode
    Network mode:router,stealth"
  ::= { mGuardNetwork 16 }

-- NETWORK_HOSTNAME
mGuardHostname OBJECT-TYPE
  SYNTAX DisplayString
  ACCESS read-write
  STATUS mandatory
  DESCRIPTION
    "Variable name: NETWORK_HOSTNAME
    WebUi Label: Hostname
    The hostname of this system"
  ::= { mGuardNetwork 8 }

-- NETWORK_HOSTNAME_MODE
mGuardHostnameMode OBJECT-TYPE
  SYNTAX INTEGER {
    userDefined(1),
    providerDefined(2)
  }
  ACCESS read-write
  STATUS mandatory
  DESCRIPTION
    "Variable name: NETWORK_HOSTNAME_MODE
    WebUi Label: Hostname mode
    Hostname mode: 1: defined by mGuardHostname, 2: provider defined (e.g.
    DHCP)"
  ::= { mGuardNetwork 9 }

-- NETWORK_PPTP_LOCALIP
mGuardPPTPLocalIP OBJECT-TYPE
  SYNTAX IpAddress
  ACCESS read-write
  STATUS mandatory
  DESCRIPTION
    "Variable name: NETWORK_PPTP_LOCALIP
    WebUi Label: Local IP
    The external IP of this system when connecting to the PPTP
    server/modem when mGuardPPTPLocalIPMode is set to static."
  ::= { mGuardPPTP 4 }

-- NETWORK_PPTP_LOGIN
mGuardPPTPLogin OBJECT-TYPE
  SYNTAX DisplayString
  ACCESS read-write
  STATUS mandatory
  DESCRIPTION
    "Variable name: NETWORK_PPTP_LOGIN
    WebUi Label: PPTP login
    PPTP login anme"
  ::= { mGuardPPTP 1 }

-- NETWORK_PPTP_MODEMIP
mGuardPPTPModemIP OBJECT-TYPE
  SYNTAX IpAddress
  ACCESS read-write
  STATUS mandatory
  DESCRIPTION
    "Variable name: NETWORK_PPTP_MODEMIP
    WebUi Label: Modem IP
    The IP of the PPTP server/modem."
  ::= { mGuardPPTP 5 }

-- NETWORK_PPTP_MODEM_MODE
mGuardPPTPLocalIPMode OBJECT-TYPE
  SYNTAX INTEGER {
    static(1),
    dhcp(2)
  }
  ACCESS read-write
  STATUS mandatory
  DESCRIPTION
    "Variable name: NETWORK_PPTP_MODEM_MODE
    WebUi Label: Local IP mode
    When set to static will use the value from mGuardPPTPLocalIP on it
    external interface connecting to the PPTP server/modem. Otherwise it
    it use DHCP."
  ::= { mGuardPPTP 3 }

-- NETWORK_PPTP_PASSWORD
mGuardPPTPassword OBJECT-TYPE
  SYNTAX DisplayString
  ACCESS read-write
  STATUS mandatory
  DESCRIPTION
    "Variable name: NETWORK_PPTP_PASSWORD
    WebUi Label: PPTP password
    PPTP password"
  ::= { mGuardPPTP 2 }


-- NETWORK_PPTP_PPPD_OPTIONS table
mGuardPPTPpppdOptionsTable OBJECT-TYPE
  SYNTAX SEQUENCE OF MGuardPPTPpppdOptionsEntry
  ACCESS not-accessible
  STATUS mandatory
  DESCRIPTION
    "A table of NETWORK_PPTP_PPPD_OPTIONS"
  ::= { mGuardPPTP 6 }

-- NETWORK_PPTP_PPPD_OPTIONS table entry
mGuardPPTPpppdOptionsEntry OBJECT-TYPE
  SYNTAX MGuardPPTPpppdOptionsEntry
  ACCESS not-accessible
  STATUS mandatory
  DESCRIPTION
    "An entry of NETWORK_PPTP_PPPD_OPTIONS"
  INDEX { mGuardPPTPpppdOptionsIndex }
  ::= { mGuardPPTPpppdOptionsTable 1 }

MGuardPPTPpppdOptionsEntry ::= SEQUENCE {
  mGuardPPTPpppdOptionsIndex               INTEGER,
  mGuardPPTPpppdOptionsValue               DisplayString,
  mGuardPPTPpppdOptionsRowStatus           RowStatus
}

-- NETWORK_PPTP_PPPD_OPTIONS table index
mGuardPPTPpppdOptionsIndex OBJECT-TYPE
  SYNTAX INTEGER (1..2147483647)
  ACCESS not-accessible
  STATUS mandatory
  DESCRIPTION
    "Index to NETWORK_PPTP_PPPD_OPTIONS"
  ::= { mGuardPPTPpppdOptionsEntry 1 }

-- NETWORK_PPTP_PPPD_OPTIONS row status
mGuardPPTPpppdOptionsRowStatus OBJECT-TYPE
  SYNTAX RowStatus
  ACCESS read-write
  STATUS mandatory
  DESCRIPTION
    "RowStatus of NETWORK_PPTP_PPPD_OPTIONS"
  ::= { mGuardPPTPpppdOptionsEntry 3 }

-- NETWORK_PPTP_PPPD_OPTIONS.OPTION
mGuardPPTPpppdOptionsValue OBJECT-TYPE
  SYNTAX DisplayString
  ACCESS read-write
  STATUS mandatory
  DESCRIPTION
    "Variable name: NETWORK_PPTP_PPPD_OPTIONS.OPTION
    WebUi Label: Option
    The pppd option."
  ::= { mGuardPPTPpppdOptionsEntry 2 }

-- NF_CONNTRACK_TCP_NOFLAGS_EST
mGuardFWConntrackTcpNoFlagsEst OBJECT-TYPE
  SYNTAX INTEGER {
    yes(1),
    no(2)
  }
  ACCESS read-write
  STATUS mandatory
  DESCRIPTION
    "Variable name: NF_CONNTRACK_TCP_NOFLAGS_EST
    WebUi Label: Allow TCP keepalive packets without TCP flags
    Allow TCP packets without flags set for established connections."
  ::= { mGuardFirewallExtended 20 }

-- NTP_ACCESS_RULES
mGuardNTPRemoteUUID OBJECT-TYPE
  SYNTAX DisplayString
  ACCESS read-only
  STATUS mandatory
  DESCRIPTION
    "Variable name: NTP_ACCESS_RULES
    WebUi Label: Allowed networks
    Universally Unique Identifier (UUID, RFC 4122) used for
    mGuardNTPFWRuleTable logging."
  ::= { mGuardNTP 7 }


-- NTP_ACCESS_RULES table
mGuardNTPFWRuleTable OBJECT-TYPE
  SYNTAX SEQUENCE OF MGuardNTPFWRuleEntry
  ACCESS not-accessible
  STATUS mandatory
  DESCRIPTION
    "A table of NTP_ACCESS_RULES"
  ::= { mGuardNTP 6 }

-- NTP_ACCESS_RULES table entry
mGuardNTPFWRuleEntry OBJECT-TYPE
  SYNTAX MGuardNTPFWRuleEntry
  ACCESS not-accessible
  STATUS mandatory
  DESCRIPTION
    "An entry of NTP_ACCESS_RULES"
  INDEX { mGuardNTPFWruleIndex }
  ::= { mGuardNTPFWRuleTable 1 }

MGuardNTPFWRuleEntry ::= SEQUENCE {
  mGuardNTPFWruleIndex                     INTEGER,
  mGuardNTPFWsourceIP                      DisplayString,
  mGuardNTPFWinterface                     INTEGER,
  mGuardNTPFWtarget                        INTEGER,
  mGuardNTPFWlog                           INTEGER,
  mGuardNTPFWRowStatus                     RowStatus,
  mGuardNTPFWcomment                       DisplayString,
  mGuardNTPFWfromMAC                       MacAddress
}

-- NTP_ACCESS_RULES table index
mGuardNTPFWruleIndex OBJECT-TYPE
  SYNTAX INTEGER (1..2147483647)
  ACCESS not-accessible
  STATUS mandatory
  DESCRIPTION
    "Index to NTP_ACCESS_RULES"
  ::= { mGuardNTPFWRuleEntry 1 }

-- NTP_ACCESS_RULES row status
mGuardNTPFWRowStatus OBJECT-TYPE
  SYNTAX RowStatus
  ACCESS read-write
  STATUS mandatory
  DESCRIPTION
    "RowStatus of NTP_ACCESS_RULES"
  ::= { mGuardNTPFWRuleEntry 6 }

-- NTP_ACCESS_RULES.COMMENT
mGuardNTPFWcomment OBJECT-TYPE
  SYNTAX DisplayString
  ACCESS read-write
  STATUS mandatory
  DESCRIPTION
    "Variable name: NTP_ACCESS_RULES.COMMENT
    WebUi Label: Comment
    Commentary or name for this rule."
  ::= { mGuardNTPFWRuleEntry 7 }

-- NTP_ACCESS_RULES.LOG
mGuardNTPFWlog OBJECT-TYPE
  SYNTAX INTEGER {
    yes(1),
    no(2)
  }
  ACCESS read-write
  STATUS mandatory
  DESCRIPTION
    "Variable name: NTP_ACCESS_RULES.LOG
    WebUi Label: Log
    Log packets matching this rule ?"
  ::= { mGuardNTPFWRuleEntry 5 }

-- NTP_ACCESS_RULES.FROM_IP
mGuardNTPFWsourceIP OBJECT-TYPE
  SYNTAX DisplayString
  ACCESS read-write
  STATUS mandatory
  DESCRIPTION
    "Variable name: NTP_ACCESS_RULES.FROM_IP
    WebUi Label: From IP
    The rule's source IP address"
  ::= { mGuardNTPFWRuleEntry 2 }

-- NTP_ACCESS_RULES.INTERFACE_DEV
mGuardNTPFWinterface OBJECT-TYPE
  SYNTAX INTEGER {
    extern(1),
    intern(2),
    extern2(3),
    dialin(4),
    viaipsec(5),
    dmz0(6),
    viagre(7)
  }
  ACCESS read-write
  STATUS mandatory
  DESCRIPTION
    "Variable name: NTP_ACCESS_RULES.INTERFACE_DEV
    WebUi Label: Interface
    The network interface the rule belongs to (extern/intern/dmz)."
  ::= { mGuardNTPFWRuleEntry 3 }

-- NTP_ACCESS_RULES.FROM_MAC
mGuardNTPFWfromMAC OBJECT-TYPE
  SYNTAX MacAddress
  ACCESS read-write
  STATUS mandatory
  DESCRIPTION
    "Variable name: NTP_ACCESS_RULES.FROM_MAC
    WebUi Label: From MAC
    The rule's source MAC address."
  ::= { mGuardNTPFWRuleEntry 8 }

-- NTP_ACCESS_RULES.TARGET
mGuardNTPFWtarget OBJECT-TYPE
  SYNTAX INTEGER {
    accept(1),
    reject(2),
    drop(3)
  }
  ACCESS read-write
  STATUS mandatory
  DESCRIPTION
    "Variable name: NTP_ACCESS_RULES.TARGET
    WebUi Label: Action
    The target of the rule (accept/reject/drop)."
  ::= { mGuardNTPFWRuleEntry 4 }

-- NTP_ENABLE
mGuardNTPactivate OBJECT-TYPE
  SYNTAX INTEGER {
    yes(1),
    no(2)
  }
  ACCESS read-write
  STATUS mandatory
  DESCRIPTION
    "Variable name: NTP_ENABLE
    WebUi Label: Enable NTP time synchronization
    Activate NTP ?"
  ::= { mGuardNTP 1 }

-- NTP_ENABLE_FILESTAMP
mGuardNTPtimestamp OBJECT-TYPE
  SYNTAX INTEGER {
    yes(1),
    no(2)
  }
  ACCESS read-write
  STATUS mandatory
  DESCRIPTION
    "Variable name: NTP_ENABLE_FILESTAMP
    WebUi Label: Time-stamp in filesystem (2h granularity)
    Time stamp in filesystem ?"
  ::= { mGuardNTP 2 }


-- NTP_SERVERS table
mGuardNTPServerTable OBJECT-TYPE
  SYNTAX SEQUENCE OF MGuardNTPServerEntry
  ACCESS not-accessible
  STATUS mandatory
  DESCRIPTION
    "A table of NTP_SERVERS"
  ::= { mGuardNTP 3 }

-- NTP_SERVERS table entry
mGuardNTPServerEntry OBJECT-TYPE
  SYNTAX MGuardNTPServerEntry
  ACCESS not-accessible
  STATUS mandatory
  DESCRIPTION
    "An entry of NTP_SERVERS"
  INDEX { mGuardNTPServerIndex }
  ::= { mGuardNTPServerTable 1 }

MGuardNTPServerEntry ::= SEQUENCE {
  mGuardNTPServerIndex                     INTEGER,
  mGuardNTPServerHost                      DisplayString,
  mGuardNTPServerRowStatus                 RowStatus,
  mGuardNTPServerPreferVPN                 INTEGER
}

-- NTP_SERVERS table index
mGuardNTPServerIndex OBJECT-TYPE
  SYNTAX INTEGER (1..2147483647)
  ACCESS not-accessible
  STATUS mandatory
  DESCRIPTION
    "Index to NTP_SERVERS"
  ::= { mGuardNTPServerEntry 1 }

-- NTP_SERVERS row status
mGuardNTPServerRowStatus OBJECT-TYPE
  SYNTAX RowStatus
  ACCESS read-write
  STATUS mandatory
  DESCRIPTION
    "RowStatus of NTP_SERVERS"
  ::= { mGuardNTPServerEntry 3 }

-- NTP_SERVERS.PREFER_VPN
mGuardNTPServerPreferVPN OBJECT-TYPE
  SYNTAX INTEGER {
    yes(1),
    no(2)
  }
  ACCESS read-write
  STATUS mandatory
  DESCRIPTION
    "Variable name: NTP_SERVERS.PREFER_VPN
    WebUi Label: Via VPN
    Access NTP Server via IPsec VPN"
  ::= { mGuardNTPServerEntry 4 }

-- NTP_SERVERS.NTP_SERVER
mGuardNTPServerHost OBJECT-TYPE
  SYNTAX DisplayString
  ACCESS read-write
  STATUS mandatory
  DESCRIPTION
    "Variable name: NTP_SERVERS.NTP_SERVER
    WebUi Label: NTP server
    Hostname or IP address of the NTP Server."
  ::= { mGuardNTPServerEntry 2 }


-- OPENVPN_CONNECTION table
mGuardOpenVPNConnectionTable OBJECT-TYPE
  SYNTAX SEQUENCE OF MGuardOpenVPNConnectionEntry
  ACCESS not-accessible
  STATUS mandatory
  DESCRIPTION
    "A table of OPENVPN_CONNECTION"
  ::= { mGuardOpenVPN 1 }

-- OPENVPN_CONNECTION table entry
mGuardOpenVPNConnectionEntry OBJECT-TYPE
  SYNTAX MGuardOpenVPNConnectionEntry
  ACCESS not-accessible
  STATUS mandatory
  DESCRIPTION
    "An entry of OPENVPN_CONNECTION"
  INDEX { mGuardOpenVPNConnectionIndex }
  ::= { mGuardOpenVPNConnectionTable 1 }

MGuardOpenVPNConnectionEntry ::= SEQUENCE {
  mGuardOpenVPNConnectionIndex             INTEGER,
  mGuardOpenVPNConnectionRowStatus         RowStatus,
  mGuardOpenVPNConnectionName              DisplayString,
  mGuardOpenVPNConnectionEnabled           INTEGER,
  mGuardOpenVPNConnectionRemoteGW          DisplayString,
  mGuardOpenVPNConnectionTimeoutSeconds    INTEGER,
  mGuardOpenVPNConnectionControl           DisplayString,
  mGuardOpenVPNConnectionControlInv        INTEGER,
  mGuardOpenVPNConnectionSmsToken          DisplayString,
  mGuardOpenVPNConnectionCompression       INTEGER,
  mGuardOpenVPNConnectionProtocol          INTEGER,
  mGuardOpenVPNConnectionLocalPort         DisplayString,
  mGuardOpenVPNConnectionRemoteLearn       INTEGER,
  mGuardOpenVPNConnectionAuth              INTEGER,
  mGuardOpenVPNConnectionLogin             DisplayString,
  mGuardOpenVPNConnectionPassword          DisplayString,
  mGuardOpenVPNConnectionLocalCertValue    INTEGER,
  mGuardOpenVPNConnectionLocalCertRef      OBJECT IDENTIFIER,
  mGuardOpenVPNConnectionCaCertValue       INTEGER,
  mGuardOpenVPNConnectionCACertRef         OBJECT IDENTIFIER,
  mGuardOpenVPNConnectionFWLogDefIn        INTEGER,
  mGuardOpenVPNConnectionFWLogDefOut       INTEGER,
  mGuardOpenVPNConnectionFWInGlobal        INTEGER,
  mGuardOpenVPNConnectionFWOutGlobal       INTEGER,
  mGuardOpenVPNConnectionEncryption        INTEGER,
  mGuardOpenVPNConnectionRekey             INTEGER,
  mGuardOpenVPNConnectionRekeyTime         INTEGER,
  mGuardOpenVPNConnectionDPDDelay          INTEGER,
  mGuardOpenVPNConnectionDPDTimeout        INTEGER,
  mGuardOpenVPNConnectionRemotePort        INTEGER,
  mGuardOpenVPNConnectionTLSAuth           DisplayString,
  mGuardOpenVPNConnectionTLSAuthKeyDirection INTEGER,
  mGuardOpenVPNLocalNat                    INTEGER,
  mGuardOpenVPNLocal                       DisplayString,
  mGuardOpenVPNLocal1to1Nat                IpAddress
}

-- OPENVPN_CONNECTION table index
mGuardOpenVPNConnectionIndex OBJECT-TYPE
  SYNTAX INTEGER (1..2147483647)
  ACCESS not-accessible
  STATUS mandatory
  DESCRIPTION
    "Index to OPENVPN_CONNECTION"
  ::= { mGuardOpenVPNConnectionEntry 1 }

-- OPENVPN_CONNECTION row status
mGuardOpenVPNConnectionRowStatus OBJECT-TYPE
  SYNTAX RowStatus
  ACCESS read-write
  STATUS mandatory
  DESCRIPTION
    "RowStatus of OPENVPN_CONNECTION"
  ::= { mGuardOpenVPNConnectionEntry 2 }

-- OPENVPN_CONNECTION.TLS_AUTH
mGuardOpenVPNConnectionTLSAuth OBJECT-TYPE
  SYNTAX DisplayString
  ACCESS read-write
  STATUS mandatory
  DESCRIPTION
    "Variable name: OPENVPN_CONNECTION.TLS_AUTH
    WebUi Label: Pre-shared key for TLS auth
    Pre-shared key (PSK) for OpenVPN TLS-Auth."
  ::= { mGuardOpenVPNConnectionEntry 33 }

-- OPENVPN_CONNECTION.PROTO_COMP
mGuardOpenVPNConnectionCompression OBJECT-TYPE
  SYNTAX INTEGER {
    yes(1),
    no(2),
    adaptive(3),
    disabled(4)
  }
  ACCESS read-write
  STATUS mandatory
  DESCRIPTION
    "Variable name: OPENVPN_CONNECTION.PROTO_COMP
    WebUi Label: Use compression
    Configure whether the OpenVPN connection should use compression."
  ::= { mGuardOpenVPNConnectionEntry 11 }

-- OPENVPN_CONNECTION.PORTFORWARDING
mGuardOpenVPNPortFWuuid OBJECT-TYPE
  SYNTAX DisplayString
  ACCESS read-only
  STATUS mandatory
  DESCRIPTION
    "Variable name: OPENVPN_CONNECTION.PORTFORWARDING
    WebUi Label: IP and port forwarding
    Universally Unique Identifier (UUID, RFC 4122) used for
    mGuardOpenVPNPortFWTable logging."
  ::= { mGuardOpenVPN 10 }


-- OPENVPN_CONNECTION.PORTFORWARDING table
mGuardOpenVPNPortFWTable OBJECT-TYPE
  SYNTAX SEQUENCE OF MGuardOpenVPNPortFWEntry
  ACCESS not-accessible
  STATUS mandatory
  DESCRIPTION
    "A table of OPENVPN_CONNECTION.PORTFORWARDING"
  ::= { mGuardOpenVPN 6 }

-- OPENVPN_CONNECTION.PORTFORWARDING table entry
mGuardOpenVPNPortFWEntry OBJECT-TYPE
  SYNTAX MGuardOpenVPNPortFWEntry
  ACCESS not-accessible
  STATUS mandatory
  DESCRIPTION
    "An entry of OPENVPN_CONNECTION.PORTFORWARDING"
  INDEX { mGuardOpenVPNConnectionIndex, mGuardOpenVPNPortFWIndex }
  ::= { mGuardOpenVPNPortFWTable 1 }

MGuardOpenVPNPortFWEntry ::= SEQUENCE {
  mGuardOpenVPNPortFWIndex                 INTEGER,
  mGuardOpenVPNPortFWRowStatus             RowStatus,
  mGuardOpenVPNPortFWComment               DisplayString,
  mGuardOpenVPNPortFWSourceIPOrGroupValue  DisplayString,
  mGuardOpenVPNPortFWSourceIPOrGroupRef    OBJECT IDENTIFIER,
  mGuardOpenVPNPortFWSPortOrGroupValue     DisplayString,
  mGuardOpenVPNPortFWSPortOrGroupRef       OBJECT IDENTIFIER,
  mGuardOpenVPNPortFWSMAC                  MacAddress,
  mGuardOpenVPNPortFWLog                   INTEGER,
  mGuardOpenVPNPortFWProto                 INTEGER,
  mGuardOpenVPNPortFWTarget                INTEGER,
  mGuardOpenVPNPortFWInPort                DisplayString,
  mGuardOpenVPNPortFWRedirectIP            DisplayString,
  mGuardOpenVPNPortFWRedirectPort          DisplayString
}

-- OPENVPN_CONNECTION.PORTFORWARDING table index
mGuardOpenVPNPortFWIndex OBJECT-TYPE
  SYNTAX INTEGER (1..2147483647)
  ACCESS not-accessible
  STATUS mandatory
  DESCRIPTION
    "Index to OPENVPN_CONNECTION.PORTFORWARDING"
  ::= { mGuardOpenVPNPortFWEntry 1 }

-- OPENVPN_CONNECTION.PORTFORWARDING row status
mGuardOpenVPNPortFWRowStatus OBJECT-TYPE
  SYNTAX RowStatus
  ACCESS read-write
  STATUS mandatory
  DESCRIPTION
    "RowStatus of OPENVPN_CONNECTION.PORTFORWARDING"
  ::= { mGuardOpenVPNPortFWEntry 2 }

-- OPENVPN_CONNECTION.PORTFORWARDING.COMMENT
mGuardOpenVPNPortFWComment OBJECT-TYPE
  SYNTAX DisplayString
  ACCESS read-write
  STATUS mandatory
  DESCRIPTION
    "Variable name: OPENVPN_CONNECTION.PORTFORWARDING.COMMENT
    WebUi Label: Comment
    Commentary or name for this rule."
  ::= { mGuardOpenVPNPortFWEntry 4 }

-- OPENVPN_CONNECTION.PORTFORWARDING.SRC_PORT
mGuardOpenVPNPortFWSPortOrGroupValue OBJECT-TYPE
  SYNTAX DisplayString
  ACCESS read-write
  STATUS mandatory
  DESCRIPTION
    "Variable name: OPENVPN_CONNECTION.PORTFORWARDING.SRC_PORT
    WebUi Label: From port
    The rule's source port"
  ::= { mGuardOpenVPNPortFWEntry 7 }

-- OPENVPN_CONNECTION.PORTFORWARDING.SRC_PORT reference
mGuardOpenVPNPortFWSPortOrGroupRef OBJECT-TYPE
  SYNTAX OBJECT IDENTIFIER
  ACCESS read-write
  STATUS mandatory
  DESCRIPTION
    "Variable name: OPENVPN_CONNECTION.PORTFORWARDING.SRC_PORT
    WebUi Label: From port
    The rule's source port as reference to port group"
  ::= { mGuardOpenVPNPortFWEntry 8 }

-- OPENVPN_CONNECTION.PORTFORWARDING.LOG
mGuardOpenVPNPortFWLog OBJECT-TYPE
  SYNTAX INTEGER {
    yes(1),
    no(2)
  }
  ACCESS read-write
  STATUS mandatory
  DESCRIPTION
    "Variable name: OPENVPN_CONNECTION.PORTFORWARDING.LOG
    WebUi Label: Log
    Log packets matching this rule."
  ::= { mGuardOpenVPNPortFWEntry 10 }

-- OPENVPN_CONNECTION.PORTFORWARDING.PROTO
mGuardOpenVPNPortFWProto OBJECT-TYPE
  SYNTAX INTEGER {
    tcp(1),
    udp(2),
    icmp(3)
  }
  ACCESS read-write
  STATUS mandatory
  DESCRIPTION
    "Variable name: OPENVPN_CONNECTION.PORTFORWARDING.PROTO
    WebUi Label: Protocol
    The rule's transport protocol"
  ::= { mGuardOpenVPNPortFWEntry 11 }

-- OPENVPN_CONNECTION.PORTFORWARDING.OUT_IP
mGuardOpenVPNPortFWRedirectIP OBJECT-TYPE
  SYNTAX DisplayString
  ACCESS read-write
  STATUS mandatory
  DESCRIPTION
    "Variable name: OPENVPN_CONNECTION.PORTFORWARDING.OUT_IP
    WebUi Label: Redirect to IP
    The rule's redirection IP."
  ::= { mGuardOpenVPNPortFWEntry 14 }

-- OPENVPN_CONNECTION.PORTFORWARDING.SRC_IP
mGuardOpenVPNPortFWSourceIPOrGroupValue OBJECT-TYPE
  SYNTAX DisplayString
  ACCESS read-write
  STATUS mandatory
  DESCRIPTION
    "Variable name: OPENVPN_CONNECTION.PORTFORWARDING.SRC_IP
    WebUi Label: From IP
    The rule's source IP address"
  ::= { mGuardOpenVPNPortFWEntry 5 }

-- OPENVPN_CONNECTION.PORTFORWARDING.SRC_IP reference
mGuardOpenVPNPortFWSourceIPOrGroupRef OBJECT-TYPE
  SYNTAX OBJECT IDENTIFIER
  ACCESS read-write
  STATUS mandatory
  DESCRIPTION
    "Variable name: OPENVPN_CONNECTION.PORTFORWARDING.SRC_IP
    WebUi Label: From IP
    The rule's source IP address as reference to IP group"
  ::= { mGuardOpenVPNPortFWEntry 6 }

-- OPENVPN_CONNECTION.PORTFORWARDING.OUT_PORT
mGuardOpenVPNPortFWRedirectPort OBJECT-TYPE
  SYNTAX DisplayString
  ACCESS read-write
  STATUS mandatory
  DESCRIPTION
    "Variable name: OPENVPN_CONNECTION.PORTFORWARDING.OUT_PORT
    WebUi Label: Redirect to port
    The rule's redirection port."
  ::= { mGuardOpenVPNPortFWEntry 15 }

-- OPENVPN_CONNECTION.PORTFORWARDING.SRC_MAC
mGuardOpenVPNPortFWSMAC OBJECT-TYPE
  SYNTAX MacAddress
  ACCESS read-write
  STATUS mandatory
  DESCRIPTION
    "Variable name: OPENVPN_CONNECTION.PORTFORWARDING.SRC_MAC
    WebUi Label: From MAC
    The rule's source MAC address."
  ::= { mGuardOpenVPNPortFWEntry 9 }

-- OPENVPN_CONNECTION.PORTFORWARDING.IN_PORT
mGuardOpenVPNPortFWInPort OBJECT-TYPE
  SYNTAX DisplayString
  ACCESS read-write
  STATUS mandatory
  DESCRIPTION
    "Variable name: OPENVPN_CONNECTION.PORTFORWARDING.IN_PORT
    WebUi Label: Incoming on port
    The rule's destination port."
  ::= { mGuardOpenVPNPortFWEntry 13 }

-- OPENVPN_CONNECTION.PORTFORWARDING.TARGET
mGuardOpenVPNPortFWTarget OBJECT-TYPE
  SYNTAX INTEGER {
    accept(1),
    reject(2),
    drop(3)
  }
  ACCESS read-write
  STATUS mandatory
  DESCRIPTION
    "Variable name: OPENVPN_CONNECTION.PORTFORWARDING.TARGET
    WebUi Label: Action
    The target of the rule (accept/reject/drop)."
  ::= { mGuardOpenVPNPortFWEntry 12 }

-- OPENVPN_CONNECTION.LOCAL_PORT
mGuardOpenVPNConnectionLocalPort OBJECT-TYPE
  SYNTAX DisplayString
  ACCESS read-write
  STATUS mandatory
  DESCRIPTION
    "Variable name: OPENVPN_CONNECTION.LOCAL_PORT
    WebUi Label: Local port
    Port on local host, used for connection. This may be a number between
    1 and 65535 or '%any'."
  ::= { mGuardOpenVPNConnectionEntry 13 }


-- OPENVPN_CONNECTION.MASQUERADE table
mGuardOpenVPNMasqueradingTable OBJECT-TYPE
  SYNTAX SEQUENCE OF MGuardOpenVPNMasqueradingEntry
  ACCESS not-accessible
  STATUS mandatory
  DESCRIPTION
    "A table of OPENVPN_CONNECTION.MASQUERADE"
  ::= { mGuardOpenVPN 5 }

-- OPENVPN_CONNECTION.MASQUERADE table entry
mGuardOpenVPNMasqueradingEntry OBJECT-TYPE
  SYNTAX MGuardOpenVPNMasqueradingEntry
  ACCESS not-accessible
  STATUS mandatory
  DESCRIPTION
    "An entry of OPENVPN_CONNECTION.MASQUERADE"
  INDEX { mGuardOpenVPNConnectionIndex, mGuardOpenVPNMasqueradingIndex }
  ::= { mGuardOpenVPNMasqueradingTable 1 }

MGuardOpenVPNMasqueradingEntry ::= SEQUENCE {
  mGuardOpenVPNMasqueradingIndex           INTEGER,
  mGuardOpenVPNMasqueradingRowStatus       RowStatus,
  mGuardOpenVPNMasqueradingComment         DisplayString,
  mGuardOpenVPNMasqueradingNet             DisplayString
}

-- OPENVPN_CONNECTION.MASQUERADE table index
mGuardOpenVPNMasqueradingIndex OBJECT-TYPE
  SYNTAX INTEGER (1..2147483647)
  ACCESS not-accessible
  STATUS mandatory
  DESCRIPTION
    "Index to OPENVPN_CONNECTION.MASQUERADE"
  ::= { mGuardOpenVPNMasqueradingEntry 1 }

-- OPENVPN_CONNECTION.MASQUERADE row status
mGuardOpenVPNMasqueradingRowStatus OBJECT-TYPE
  SYNTAX RowStatus
  ACCESS read-write
  STATUS mandatory
  DESCRIPTION
    "RowStatus of OPENVPN_CONNECTION.MASQUERADE"
  ::= { mGuardOpenVPNMasqueradingEntry 2 }

-- OPENVPN_CONNECTION.MASQUERADE.COMMENT
mGuardOpenVPNMasqueradingComment OBJECT-TYPE
  SYNTAX DisplayString
  ACCESS read-write
  STATUS mandatory
  DESCRIPTION
    "Variable name: OPENVPN_CONNECTION.MASQUERADE.COMMENT
    WebUi Label: Comment
    Commentary or name for this rule."
  ::= { mGuardOpenVPNMasqueradingEntry 3 }

-- OPENVPN_CONNECTION.MASQUERADE.NET
mGuardOpenVPNMasqueradingNet OBJECT-TYPE
  SYNTAX DisplayString
  ACCESS read-write
  STATUS mandatory
  DESCRIPTION
    "Variable name: OPENVPN_CONNECTION.MASQUERADE.NET
    WebUi Label: Network
    The network to masquerade."
  ::= { mGuardOpenVPNMasqueradingEntry 4 }

-- OPENVPN_CONNECTION.TLS_AUTH_KEY_DIRECTION
mGuardOpenVPNConnectionTLSAuthKeyDirection OBJECT-TYPE
  SYNTAX INTEGER {
    none(1),
    dir0(2),
    dir1(3)
  }
  ACCESS read-write
  STATUS mandatory
  DESCRIPTION
    "Variable name: OPENVPN_CONNECTION.TLS_AUTH_KEY_DIRECTION
    WebUi Label: Key direction for TLS auth
    Key direction for PSK for OpenVPN TLS-Auth."
  ::= { mGuardOpenVPNConnectionEntry 34 }

-- OPENVPN_CONNECTION.VPN_ENCRYPTION
mGuardOpenVPNConnectionEncryption OBJECT-TYPE
  SYNTAX INTEGER {
    aes-128-cbc(1),
    aes-192-cbc(2),
    aes-256-cbc(3),
    bf-cbc(4)
  }
  ACCESS read-write
  STATUS mandatory
  DESCRIPTION
    "Variable name: OPENVPN_CONNECTION.VPN_ENCRYPTION
    WebUi Label: Encryption algorithm
    Encryption used for the OpenVPN connection."
  ::= { mGuardOpenVPNConnectionEntry 27 }

-- OPENVPN_CONNECTION.RENEG
mGuardOpenVPNConnectionRekey OBJECT-TYPE
  SYNTAX INTEGER {
    yes(1),
    no(2)
  }
  ACCESS read-write
  STATUS mandatory
  DESCRIPTION
    "Variable name: OPENVPN_CONNECTION.RENEG
    WebUi Label: Key renegotiation
    Renegotiate connection after the keys have expired? Must be set to
    'no' on both end to be effective."
  ::= { mGuardOpenVPNConnectionEntry 28 }

-- OPENVPN_CONNECTION.SMS_TOKEN
mGuardOpenVPNConnectionSmsToken OBJECT-TYPE
  SYNTAX DisplayString
  ACCESS read-write
  STATUS mandatory
  DESCRIPTION
    "Variable name: OPENVPN_CONNECTION.SMS_TOKEN
    WebUi Label: Token for text message trigger
    Define a token to disable/enable the OpenVPN connection per SMS."
  ::= { mGuardOpenVPNConnectionEntry 10 }

-- OPENVPN_CONNECTION.LOGIN
mGuardOpenVPNConnectionLogin OBJECT-TYPE
  SYNTAX DisplayString
  ACCESS read-write
  STATUS mandatory
  DESCRIPTION
    "Variable name: OPENVPN_CONNECTION.LOGIN
    WebUi Label: User name
    Login or username, if 'simple' authentication is used."
  ::= { mGuardOpenVPNConnectionEntry 17 }

-- OPENVPN_CONNECTION.CONTROL
mGuardOpenVPNConnectionControl OBJECT-TYPE
  SYNTAX DisplayString
  ACCESS read-write
  STATUS mandatory
  DESCRIPTION
    "Variable name: OPENVPN_CONNECTION.CONTROL
    WebUi Label: Controlling service input
    Write 'cmd1', 'cmd2' or 'cmd3' to this object to control this OpenVPN
    connection with a command switch. Write 'none' to disable this
    feature."
  ::= { mGuardOpenVPNConnectionEntry 8 }

-- OPENVPN_CONNECTION.REMOTE_LEARN
mGuardOpenVPNConnectionRemoteLearn OBJECT-TYPE
  SYNTAX INTEGER {
    yes(1),
    no(2)
  }
  ACCESS read-write
  STATUS mandatory
  DESCRIPTION
    "Variable name: OPENVPN_CONNECTION.REMOTE_LEARN
    WebUi Label: Learn remote routes from server
    Introduce routes learned from the OpenVPN remote peer."
  ::= { mGuardOpenVPNConnectionEntry 15 }

-- OPENVPN_CONNECTION.REMOTE_PORT
mGuardOpenVPNConnectionRemotePort OBJECT-TYPE
  SYNTAX INTEGER(1..65535)
  ACCESS read-write
  STATUS mandatory
  DESCRIPTION
    "Variable name: OPENVPN_CONNECTION.REMOTE_PORT
    WebUi Label: Remote port
    Port on remote peer, used for connection. This should be a number
    between 1 and 65535."
  ::= { mGuardOpenVPNConnectionEntry 32 }

-- OPENVPN_CONNECTION.CONTROL_INV
mGuardOpenVPNConnectionControlInv OBJECT-TYPE
  SYNTAX INTEGER {
    yes(1),
    no(2)
  }
  ACCESS read-write
  STATUS mandatory
  DESCRIPTION
    "Variable name: OPENVPN_CONNECTION.CONTROL_INV
    WebUi Label: Use inverted control logic
    Configure whether the control input is low active."
  ::= { mGuardOpenVPNConnectionEntry 9 }

-- OPENVPN_CONNECTION.FW_OUTGOING_GLOBAL
mGuardOpenVPNConnectionFWOutGlobal OBJECT-TYPE
  SYNTAX INTEGER {
    accept(1),
    drop(2),
    rules(3),
    ping(4)
  }
  ACCESS read-write
  STATUS mandatory
  DESCRIPTION
    "Variable name: OPENVPN_CONNECTION.FW_OUTGOING_GLOBAL
    WebUi Label: General firewall setting
    Global switch to accept or drop all outgoing connections or to follow
    the explicit firewall rules."
  ::= { mGuardOpenVPNConnectionEntry 26 }

-- OPENVPN_CONNECTION.VPN_START
mGuardOpenVPNConnectionEnabled OBJECT-TYPE
  SYNTAX INTEGER {
    disabled(1),
    stopped(2),
    started(3)
  }
  ACCESS read-write
  STATUS mandatory
  DESCRIPTION
    "Variable name: OPENVPN_CONNECTION.VPN_START
    WebUi Label: Initial mode
    Status of the connection. It can be enabled here and be set to the
    status 'stopped' or 'started'."
  ::= { mGuardOpenVPNConnectionEntry 5 }

-- OPENVPN_CONNECTION.CA_CERT_REF
mGuardOpenVPNConnectionCaCertValue OBJECT-TYPE
  SYNTAX INTEGER {
    none(1)
  }
  ACCESS read-write
  STATUS mandatory
  DESCRIPTION
    "Variable name: OPENVPN_CONNECTION.CA_CERT_REF
    WebUi Label: CA certificate (for verification of server certificate)
    "
  ::= { mGuardOpenVPNConnectionEntry 21 }

-- OPENVPN_CONNECTION.CA_CERT_REF reference
mGuardOpenVPNConnectionCACertRef OBJECT-TYPE
  SYNTAX OBJECT IDENTIFIER
  ACCESS read-write
  STATUS mandatory
  DESCRIPTION
    "Variable name: OPENVPN_CONNECTION.CA_CERT_REF
    WebUi Label: CA certificate (for verification of server certificate)
    CA certificate to check validity of remote OpenVPN peers X509
    certificate. This object may contain the OID of a
    'mGuardCertsCAIndex'."
  ::= { mGuardOpenVPNConnectionEntry 22 }

-- OPENVPN_CONNECTION.FW_INCOMING_GLOBAL
mGuardOpenVPNConnectionFWInGlobal OBJECT-TYPE
  SYNTAX INTEGER {
    accept(1),
    drop(2),
    rules(3),
    ping(4)
  }
  ACCESS read-write
  STATUS mandatory
  DESCRIPTION
    "Variable name: OPENVPN_CONNECTION.FW_INCOMING_GLOBAL
    WebUi Label: General firewall setting
    Global switch to accept or drop all incoming connections or to follow
    the explicit firewall rules."
  ::= { mGuardOpenVPNConnectionEntry 25 }

-- OPENVPN_CONNECTION.PROTOCOL
mGuardOpenVPNConnectionProtocol OBJECT-TYPE
  SYNTAX INTEGER {
    tcp(6),
    udp(17)
  }
  ACCESS read-write
  STATUS mandatory
  DESCRIPTION
    "Variable name: OPENVPN_CONNECTION.PROTOCOL
    WebUi Label: Protocol
    Transport protocol used for OpenVPN connection."
  ::= { mGuardOpenVPNConnectionEntry 12 }

-- OPENVPN_CONNECTION.VPN_NAME
mGuardOpenVPNConnectionName OBJECT-TYPE
  SYNTAX DisplayString
  ACCESS read-write
  STATUS mandatory
  DESCRIPTION
    "Variable name: OPENVPN_CONNECTION.VPN_NAME
    WebUi Label: A descriptive name for the connection
    Descriptive name of the OpenVPN connection, used for referencing in
    GUI."
  ::= { mGuardOpenVPNConnectionEntry 4 }

-- OPENVPN_CONNECTION.VPN_GW
mGuardOpenVPNConnectionRemoteGW OBJECT-TYPE
  SYNTAX DisplayString
  ACCESS read-write
  STATUS mandatory
  DESCRIPTION
    "Variable name: OPENVPN_CONNECTION.VPN_GW
    WebUi Label: Address of the remote site's VPN gateway (IP address or hostname)
    Name or IP address of OpenVPN remote peer."
  ::= { mGuardOpenVPNConnectionEntry 6 }

-- OPENVPN_CONNECTION.FW_OUTGOING
mGuardOpenVPNFWOUTuuid OBJECT-TYPE
  SYNTAX DisplayString
  ACCESS read-only
  STATUS mandatory
  DESCRIPTION
    "Variable name: OPENVPN_CONNECTION.FW_OUTGOING
    WebUi Label: --
    Universally Unique Identifier (UUID, RFC 4122) used for
    mGuardOpenVPNFWOUTTable logging."
  ::= { mGuardOpenVPN 9 }


-- OPENVPN_CONNECTION.FW_OUTGOING table
mGuardOpenVPNFWOUTTable OBJECT-TYPE
  SYNTAX SEQUENCE OF MGuardOpenVPNFWOUTEntry
  ACCESS not-accessible
  STATUS mandatory
  DESCRIPTION
    "A table of OPENVPN_CONNECTION.FW_OUTGOING"
  ::= { mGuardOpenVPN 4 }

-- OPENVPN_CONNECTION.FW_OUTGOING table entry
mGuardOpenVPNFWOUTEntry OBJECT-TYPE
  SYNTAX MGuardOpenVPNFWOUTEntry
  ACCESS not-accessible
  STATUS mandatory
  DESCRIPTION
    "An entry of OPENVPN_CONNECTION.FW_OUTGOING"
  INDEX { mGuardOpenVPNConnectionIndex, mGuardOpenVPNFWOUTIndex }
  ::= { mGuardOpenVPNFWOUTTable 1 }

MGuardOpenVPNFWOUTEntry ::= SEQUENCE {
  mGuardOpenVPNFWOUTIndex                  INTEGER,
  mGuardOpenVPNFWOUTRowStatus              RowStatus,
  mGuardOpenVPNFWOUTComment                DisplayString,
  mGuardOpenVPNFWOUTSourceIPOrGroupValue   DisplayString,
  mGuardOpenVPNFWOUTSourceIPOrGroupRef     OBJECT IDENTIFIER,
  mGuardOpenVPNFWOUTDestinationIPOrGroupValue DisplayString,
  mGuardOpenVPNFWOUTDestinationIPOrGroupRef OBJECT IDENTIFIER,
  mGuardOpenVPNFWOUTSPortOrGroupValue      DisplayString,
  mGuardOpenVPNFWOUTSPortOrGroupRef        OBJECT IDENTIFIER,
  mGuardOpenVPNFWOUTDPortOrGroupValue      DisplayString,
  mGuardOpenVPNFWOUTDPortOrGroupRef        OBJECT IDENTIFIER,
  mGuardOpenVPNFWOUTLog                    INTEGER,
  mGuardOpenVPNFWOUTProto                  INTEGER,
  mGuardOpenVPNFWOUTTargetValue            INTEGER,
  mGuardOpenVPNFWOUTTargetRef              OBJECT IDENTIFIER
}

-- OPENVPN_CONNECTION.FW_OUTGOING table index
mGuardOpenVPNFWOUTIndex OBJECT-TYPE
  SYNTAX INTEGER (1..2147483647)
  ACCESS not-accessible
  STATUS mandatory
  DESCRIPTION
    "Index to OPENVPN_CONNECTION.FW_OUTGOING"
  ::= { mGuardOpenVPNFWOUTEntry 1 }

-- OPENVPN_CONNECTION.FW_OUTGOING row status
mGuardOpenVPNFWOUTRowStatus OBJECT-TYPE
  SYNTAX RowStatus
  ACCESS read-write
  STATUS mandatory
  DESCRIPTION
    "RowStatus of OPENVPN_CONNECTION.FW_OUTGOING"
  ::= { mGuardOpenVPNFWOUTEntry 2 }

-- OPENVPN_CONNECTION.FW_OUTGOING.COMMENT
mGuardOpenVPNFWOUTComment OBJECT-TYPE
  SYNTAX DisplayString
  ACCESS read-write
  STATUS mandatory
  DESCRIPTION
    "Variable name: OPENVPN_CONNECTION.FW_OUTGOING.COMMENT
    WebUi Label: Comment
    Commentary or name for this rule."
  ::= { mGuardOpenVPNFWOUTEntry 4 }

-- OPENVPN_CONNECTION.FW_OUTGOING.FROM_PORT
mGuardOpenVPNFWOUTSPortOrGroupValue OBJECT-TYPE
  SYNTAX DisplayString
  ACCESS read-write
  STATUS mandatory
  DESCRIPTION
    "Variable name: OPENVPN_CONNECTION.FW_OUTGOING.FROM_PORT
    WebUi Label: From port
    The rule's source port"
  ::= { mGuardOpenVPNFWOUTEntry 9 }

-- OPENVPN_CONNECTION.FW_OUTGOING.FROM_PORT reference
mGuardOpenVPNFWOUTSPortOrGroupRef OBJECT-TYPE
  SYNTAX OBJECT IDENTIFIER
  ACCESS read-write
  STATUS mandatory
  DESCRIPTION
    "Variable name: OPENVPN_CONNECTION.FW_OUTGOING.FROM_PORT
    WebUi Label: From port
    The rule's source port as reference to port group"
  ::= { mGuardOpenVPNFWOUTEntry 10 }

-- OPENVPN_CONNECTION.FW_OUTGOING.LOG
mGuardOpenVPNFWOUTLog OBJECT-TYPE
  SYNTAX INTEGER {
    yes(1),
    no(2)
  }
  ACCESS read-write
  STATUS mandatory
  DESCRIPTION
    "Variable name: OPENVPN_CONNECTION.FW_OUTGOING.LOG
    WebUi Label: Log
    Log packets matching this rule."
  ::= { mGuardOpenVPNFWOUTEntry 13 }

-- OPENVPN_CONNECTION.FW_OUTGOING.PROTO
mGuardOpenVPNFWOUTProto OBJECT-TYPE
  SYNTAX INTEGER {
    tcp(1),
    udp(2),
    icmp(3),
    all(4),
    gre(5)
  }
  ACCESS read-write
  STATUS mandatory
  DESCRIPTION
    "Variable name: OPENVPN_CONNECTION.FW_OUTGOING.PROTO
    WebUi Label: Protocol
    The rule's transport protocol"
  ::= { mGuardOpenVPNFWOUTEntry 14 }

-- OPENVPN_CONNECTION.FW_OUTGOING.FROM_IP
mGuardOpenVPNFWOUTSourceIPOrGroupValue OBJECT-TYPE
  SYNTAX DisplayString
  ACCESS read-write
  STATUS mandatory
  DESCRIPTION
    "Variable name: OPENVPN_CONNECTION.FW_OUTGOING.FROM_IP
    WebUi Label: From IP
    The rule's source IP address"
  ::= { mGuardOpenVPNFWOUTEntry 5 }

-- OPENVPN_CONNECTION.FW_OUTGOING.FROM_IP reference
mGuardOpenVPNFWOUTSourceIPOrGroupRef OBJECT-TYPE
  SYNTAX OBJECT IDENTIFIER
  ACCESS read-write
  STATUS mandatory
  DESCRIPTION
    "Variable name: OPENVPN_CONNECTION.FW_OUTGOING.FROM_IP
    WebUi Label: From IP
    The rule's source IP address as reference to IP group"
  ::= { mGuardOpenVPNFWOUTEntry 6 }

-- OPENVPN_CONNECTION.FW_OUTGOING.IN_IP
mGuardOpenVPNFWOUTDestinationIPOrGroupValue OBJECT-TYPE
  SYNTAX DisplayString
  ACCESS read-write
  STATUS mandatory
  DESCRIPTION
    "Variable name: OPENVPN_CONNECTION.FW_OUTGOING.IN_IP
    WebUi Label: To IP
    The rule's destination IP address"
  ::= { mGuardOpenVPNFWOUTEntry 7 }

-- OPENVPN_CONNECTION.FW_OUTGOING.IN_IP reference
mGuardOpenVPNFWOUTDestinationIPOrGroupRef OBJECT-TYPE
  SYNTAX OBJECT IDENTIFIER
  ACCESS read-write
  STATUS mandatory
  DESCRIPTION
    "Variable name: OPENVPN_CONNECTION.FW_OUTGOING.IN_IP
    WebUi Label: To IP
    The rule's destination IP address as reference to IP group"
  ::= { mGuardOpenVPNFWOUTEntry 8 }

-- OPENVPN_CONNECTION.FW_OUTGOING.TARGET_REF
mGuardOpenVPNFWOUTTargetValue OBJECT-TYPE
  SYNTAX INTEGER {
    accept(1),
    reject(2),
    drop(3)
  }
  ACCESS read-write
  STATUS mandatory
  DESCRIPTION
    "Variable name: OPENVPN_CONNECTION.FW_OUTGOING.TARGET_REF
    WebUi Label: Action
    The rule's target. This object is effective if and only if the
    'mGuardOpenVPNFWOUTTargetRef' object contains the OID of this object."
  ::= { mGuardOpenVPNFWOUTEntry 15 }

-- OPENVPN_CONNECTION.FW_OUTGOING.TARGET_REF reference
mGuardOpenVPNFWOUTTargetRef OBJECT-TYPE
  SYNTAX OBJECT IDENTIFIER
  ACCESS read-write
  STATUS mandatory
  DESCRIPTION
    "Variable name: OPENVPN_CONNECTION.FW_OUTGOING.TARGET_REF
    WebUi Label: Action
    Set this object to the OID of an 'mGuardFWRuleIndex' to select a
    firewall ruleset as this rule's target. Set this object to the OID of
    the 'mGuardOpenVPNFWOUTTargetValue' object to choose a target from
    that objects range."
  ::= { mGuardOpenVPNFWOUTEntry 16 }

-- OPENVPN_CONNECTION.FW_OUTGOING.IN_PORT
mGuardOpenVPNFWOUTDPortOrGroupValue OBJECT-TYPE
  SYNTAX DisplayString
  ACCESS read-write
  STATUS mandatory
  DESCRIPTION
    "Variable name: OPENVPN_CONNECTION.FW_OUTGOING.IN_PORT
    WebUi Label: To port
    The rule's destination port"
  ::= { mGuardOpenVPNFWOUTEntry 11 }

-- OPENVPN_CONNECTION.FW_OUTGOING.IN_PORT reference
mGuardOpenVPNFWOUTDPortOrGroupRef OBJECT-TYPE
  SYNTAX OBJECT IDENTIFIER
  ACCESS read-write
  STATUS mandatory
  DESCRIPTION
    "Variable name: OPENVPN_CONNECTION.FW_OUTGOING.IN_PORT
    WebUi Label: To port
    The rule's destination port as reference to port group"
  ::= { mGuardOpenVPNFWOUTEntry 12 }

-- OPENVPN_CONNECTION.LOCAL_1TO1NAT
mGuardOpenVPNLocal1to1Nat OBJECT-TYPE
  SYNTAX IpAddress
  ACCESS read-write
  STATUS mandatory
  DESCRIPTION
    "Variable name: OPENVPN_CONNECTION.LOCAL_1TO1NAT
    WebUi Label: Local address for 1:1 NAT
    Local address for 1-to-1 NAT."
  ::= { mGuardOpenVPNConnectionEntry 37 }

-- OPENVPN_CONNECTION.LOCAL_NAT
mGuardOpenVPNLocalNat OBJECT-TYPE
  SYNTAX INTEGER {
    none(1),
    use1to1nat(2),
    masq(3)
  }
  ACCESS read-write
  STATUS mandatory
  DESCRIPTION
    "Variable name: OPENVPN_CONNECTION.LOCAL_NAT
    WebUi Label: Local NAT for OpenVPN connections
    Enable 1-to-1 NAT or masquerading of the local network in router mode."
  ::= { mGuardOpenVPNConnectionEntry 35 }

-- OPENVPN_CONNECTION.DPD_DELAY
mGuardOpenVPNConnectionDPDDelay OBJECT-TYPE
  SYNTAX INTEGER(0..600)
  ACCESS read-write
  STATUS mandatory
  DESCRIPTION
    "Variable name: OPENVPN_CONNECTION.DPD_DELAY
    WebUi Label: Delay between requests for a sign of life
    Interval in seconds to wait before sending DPD pings if no any other
    data is sent. The default value is 0, which means no DPD pings are
    sent."
  ::= { mGuardOpenVPNConnectionEntry 30 }

-- OPENVPN_CONNECTION.LOCAL_CERT_REF
mGuardOpenVPNConnectionLocalCertValue OBJECT-TYPE
  SYNTAX INTEGER {
    none(1)
  }
  ACCESS read-write
  STATUS mandatory
  DESCRIPTION
    "Variable name: OPENVPN_CONNECTION.LOCAL_CERT_REF
    WebUi Label: Local X.509 certificate
    "
  ::= { mGuardOpenVPNConnectionEntry 19 }

-- OPENVPN_CONNECTION.LOCAL_CERT_REF reference
mGuardOpenVPNConnectionLocalCertRef OBJECT-TYPE
  SYNTAX OBJECT IDENTIFIER
  ACCESS read-write
  STATUS mandatory
  DESCRIPTION
    "Variable name: OPENVPN_CONNECTION.LOCAL_CERT_REF
    WebUi Label: Local X.509 certificate
    Local certificate for authentication against the OpenVPN peer, if
    'x509' authentication is used. This object may contain the OID of a
    'mGuardCertsLocalIndex'."
  ::= { mGuardOpenVPNConnectionEntry 20 }

-- OPENVPN_CONNECTION.PASSWORD
mGuardOpenVPNConnectionPassword OBJECT-TYPE
  SYNTAX DisplayString
  ACCESS read-write
  STATUS mandatory
  DESCRIPTION
    "Variable name: OPENVPN_CONNECTION.PASSWORD
    WebUi Label: Password
    Password, if 'simple' authentication is used."
  ::= { mGuardOpenVPNConnectionEntry 18 }

-- OPENVPN_CONNECTION.LOCAL
mGuardOpenVPNLocal OBJECT-TYPE
  SYNTAX DisplayString
  ACCESS read-write
  STATUS mandatory
  DESCRIPTION
    "Variable name: OPENVPN_CONNECTION.LOCAL
    WebUi Label: Virtual local network for 1:1 NAT
    Virtual local network for 1-to-1 NAT in CIDR notation."
  ::= { mGuardOpenVPNConnectionEntry 36 }


-- OPENVPN_CONNECTION.REMOTE table
mGuardOpenVPNRemoteNetTable OBJECT-TYPE
  SYNTAX SEQUENCE OF MGuardOpenVPNRemoteNetEntry
  ACCESS not-accessible
  STATUS mandatory
  DESCRIPTION
    "A table of OPENVPN_CONNECTION.REMOTE"
  ::= { mGuardOpenVPN 2 }

-- OPENVPN_CONNECTION.REMOTE table entry
mGuardOpenVPNRemoteNetEntry OBJECT-TYPE
  SYNTAX MGuardOpenVPNRemoteNetEntry
  ACCESS not-accessible
  STATUS mandatory
  DESCRIPTION
    "An entry of OPENVPN_CONNECTION.REMOTE"
  INDEX { mGuardOpenVPNConnectionIndex, mGuardOpenVPNRemoteNetIndex }
  ::= { mGuardOpenVPNRemoteNetTable 1 }

MGuardOpenVPNRemoteNetEntry ::= SEQUENCE {
  mGuardOpenVPNRemoteNetIndex              INTEGER,
  mGuardOpenVPNRemoteNetRowStatus          RowStatus,
  mGuardOpenVPNRemoteNetComment            DisplayString,
  mGuardOpenVPNRemoteNetValue              DisplayString
}

-- OPENVPN_CONNECTION.REMOTE table index
mGuardOpenVPNRemoteNetIndex OBJECT-TYPE
  SYNTAX INTEGER (1..2147483647)
  ACCESS not-accessible
  STATUS mandatory
  DESCRIPTION
    "Index to OPENVPN_CONNECTION.REMOTE"
  ::= { mGuardOpenVPNRemoteNetEntry 1 }

-- OPENVPN_CONNECTION.REMOTE row status
mGuardOpenVPNRemoteNetRowStatus OBJECT-TYPE
  SYNTAX RowStatus
  ACCESS read-write
  STATUS mandatory
  DESCRIPTION
    "RowStatus of OPENVPN_CONNECTION.REMOTE"
  ::= { mGuardOpenVPNRemoteNetEntry 2 }

-- OPENVPN_CONNECTION.REMOTE.COMMENT
mGuardOpenVPNRemoteNetComment OBJECT-TYPE
  SYNTAX DisplayString
  ACCESS read-write
  STATUS mandatory
  DESCRIPTION
    "Variable name: OPENVPN_CONNECTION.REMOTE.COMMENT
    WebUi Label: Comment
    Comment to describe the remote network."
  ::= { mGuardOpenVPNRemoteNetEntry 3 }

-- OPENVPN_CONNECTION.REMOTE.NET
mGuardOpenVPNRemoteNetValue OBJECT-TYPE
  SYNTAX DisplayString
  ACCESS read-write
  STATUS mandatory
  DESCRIPTION
    "Variable name: OPENVPN_CONNECTION.REMOTE.NET
    WebUi Label: Network
    Remote IPv4 address or net."
  ::= { mGuardOpenVPNRemoteNetEntry 4 }

-- OPENVPN_CONNECTION.DPD_TIMEOUT
mGuardOpenVPNConnectionDPDTimeout OBJECT-TYPE
  SYNTAX INTEGER(0..600)
  ACCESS read-write
  STATUS mandatory
  DESCRIPTION
    "Variable name: OPENVPN_CONNECTION.DPD_TIMEOUT
    WebUi Label: Timeout for absent sign of life after which peer is assumed dead
    Interval in seconds before declaring the remote end as dead, when no
    packets are received. The default value is 0, which means never
    declaring the remote peer as dead automatically."
  ::= { mGuardOpenVPNConnectionEntry 31 }

-- OPENVPN_CONNECTION.TIMEOUT_SECONDS
mGuardOpenVPNConnectionTimeoutSeconds OBJECT-TYPE
  SYNTAX INTEGER(0..2592000)
  ACCESS read-write
  STATUS mandatory
  DESCRIPTION
    "Variable name: OPENVPN_CONNECTION.TIMEOUT_SECONDS
    WebUi Label: Deactivation timeout
    Specifies the timeout after that a OpenVPN connection will be stopped."
  ::= { mGuardOpenVPNConnectionEntry 7 }

-- OPENVPN_CONNECTION.RENEGTIME
mGuardOpenVPNConnectionRekeyTime OBJECT-TYPE
  SYNTAX INTEGER(60..86400)
  ACCESS read-write
  STATUS mandatory
  DESCRIPTION
    "Variable name: OPENVPN_CONNECTION.RENEGTIME
    WebUi Label: Key renegotiation interval
    Rekey time/timeout in seconds."
  ::= { mGuardOpenVPNConnectionEntry 29 }

-- OPENVPN_CONNECTION.FW_INCOMING
mGuardOpenVPNFWINuuid OBJECT-TYPE
  SYNTAX DisplayString
  ACCESS read-only
  STATUS mandatory
  DESCRIPTION
    "Variable name: OPENVPN_CONNECTION.FW_INCOMING
    WebUi Label: --
    Universally Unique Identifier (UUID, RFC 4122) used for
    mGuardOpenVPNFWINTable logging."
  ::= { mGuardOpenVPN 8 }


-- OPENVPN_CONNECTION.FW_INCOMING table
mGuardOpenVPNFWINTable OBJECT-TYPE
  SYNTAX SEQUENCE OF MGuardOpenVPNFWINEntry
  ACCESS not-accessible
  STATUS mandatory
  DESCRIPTION
    "A table of OPENVPN_CONNECTION.FW_INCOMING"
  ::= { mGuardOpenVPN 3 }

-- OPENVPN_CONNECTION.FW_INCOMING table entry
mGuardOpenVPNFWINEntry OBJECT-TYPE
  SYNTAX MGuardOpenVPNFWINEntry
  ACCESS not-accessible
  STATUS mandatory
  DESCRIPTION
    "An entry of OPENVPN_CONNECTION.FW_INCOMING"
  INDEX { mGuardOpenVPNConnectionIndex, mGuardOpenVPNFWINIndex }
  ::= { mGuardOpenVPNFWINTable 1 }

MGuardOpenVPNFWINEntry ::= SEQUENCE {
  mGuardOpenVPNFWINIndex                   INTEGER,
  mGuardOpenVPNFWINRowStatus               RowStatus,
  mGuardOpenVPNFWINComment                 DisplayString,
  mGuardOpenVPNFWINSourceIPOrGroupValue    DisplayString,
  mGuardOpenVPNFWINSourceIPOrGroupRef      OBJECT IDENTIFIER,
  mGuardOpenVPNFWINDestinationIPOrGroupValue DisplayString,
  mGuardOpenVPNFWINDestinationIPOrGroupRef OBJECT IDENTIFIER,
  mGuardOpenVPNFWINSPortOrGroupValue       DisplayString,
  mGuardOpenVPNFWINSPortOrGroupRef         OBJECT IDENTIFIER,
  mGuardOpenVPNFWINDPortOrGroupValue       DisplayString,
  mGuardOpenVPNFWINDPortOrGroupRef         OBJECT IDENTIFIER,
  mGuardOpenVPNFWINLog                     INTEGER,
  mGuardOpenVPNFWINProto                   INTEGER,
  mGuardOpenVPNFWINTargetValue             INTEGER,
  mGuardOpenVPNFWINTargetRef               OBJECT IDENTIFIER
}

-- OPENVPN_CONNECTION.FW_INCOMING table index
mGuardOpenVPNFWINIndex OBJECT-TYPE
  SYNTAX INTEGER (1..2147483647)
  ACCESS not-accessible
  STATUS mandatory
  DESCRIPTION
    "Index to OPENVPN_CONNECTION.FW_INCOMING"
  ::= { mGuardOpenVPNFWINEntry 1 }

-- OPENVPN_CONNECTION.FW_INCOMING row status
mGuardOpenVPNFWINRowStatus OBJECT-TYPE
  SYNTAX RowStatus
  ACCESS read-write
  STATUS mandatory
  DESCRIPTION
    "RowStatus of OPENVPN_CONNECTION.FW_INCOMING"
  ::= { mGuardOpenVPNFWINEntry 2 }

-- OPENVPN_CONNECTION.FW_INCOMING.COMMENT
mGuardOpenVPNFWINComment OBJECT-TYPE
  SYNTAX DisplayString
  ACCESS read-write
  STATUS mandatory
  DESCRIPTION
    "Variable name: OPENVPN_CONNECTION.FW_INCOMING.COMMENT
    WebUi Label: Comment
    Commentary or name for this rule."
  ::= { mGuardOpenVPNFWINEntry 4 }

-- OPENVPN_CONNECTION.FW_INCOMING.FROM_PORT
mGuardOpenVPNFWINSPortOrGroupValue OBJECT-TYPE
  SYNTAX DisplayString
  ACCESS read-write
  STATUS mandatory
  DESCRIPTION
    "Variable name: OPENVPN_CONNECTION.FW_INCOMING.FROM_PORT
    WebUi Label: From port
    The rule's source port"
  ::= { mGuardOpenVPNFWINEntry 9 }

-- OPENVPN_CONNECTION.FW_INCOMING.FROM_PORT reference
mGuardOpenVPNFWINSPortOrGroupRef OBJECT-TYPE
  SYNTAX OBJECT IDENTIFIER
  ACCESS read-write
  STATUS mandatory
  DESCRIPTION
    "Variable name: OPENVPN_CONNECTION.FW_INCOMING.FROM_PORT
    WebUi Label: From port
    The rule's source port as reference to port group"
  ::= { mGuardOpenVPNFWINEntry 10 }

-- OPENVPN_CONNECTION.FW_INCOMING.LOG
mGuardOpenVPNFWINLog OBJECT-TYPE
  SYNTAX INTEGER {
    yes(1),
    no(2)
  }
  ACCESS read-write
  STATUS mandatory
  DESCRIPTION
    "Variable name: OPENVPN_CONNECTION.FW_INCOMING.LOG
    WebUi Label: Log
    Log packets matching this rule."
  ::= { mGuardOpenVPNFWINEntry 13 }

-- OPENVPN_CONNECTION.FW_INCOMING.PROTO
mGuardOpenVPNFWINProto OBJECT-TYPE
  SYNTAX INTEGER {
    tcp(1),
    udp(2),
    icmp(3),
    all(4),
    gre(5)
  }
  ACCESS read-write
  STATUS mandatory
  DESCRIPTION
    "Variable name: OPENVPN_CONNECTION.FW_INCOMING.PROTO
    WebUi Label: Protocol
    The rule's transport protocol"
  ::= { mGuardOpenVPNFWINEntry 14 }

-- OPENVPN_CONNECTION.FW_INCOMING.FROM_IP
mGuardOpenVPNFWINSourceIPOrGroupValue OBJECT-TYPE
  SYNTAX DisplayString
  ACCESS read-write
  STATUS mandatory
  DESCRIPTION
    "Variable name: OPENVPN_CONNECTION.FW_INCOMING.FROM_IP
    WebUi Label: From IP
    The rule's source IP address"
  ::= { mGuardOpenVPNFWINEntry 5 }

-- OPENVPN_CONNECTION.FW_INCOMING.FROM_IP reference
mGuardOpenVPNFWINSourceIPOrGroupRef OBJECT-TYPE
  SYNTAX OBJECT IDENTIFIER
  ACCESS read-write
  STATUS mandatory
  DESCRIPTION
    "Variable name: OPENVPN_CONNECTION.FW_INCOMING.FROM_IP
    WebUi Label: From IP
    The rule's source IP address as reference to IP group"
  ::= { mGuardOpenVPNFWINEntry 6 }

-- OPENVPN_CONNECTION.FW_INCOMING.IN_IP
mGuardOpenVPNFWINDestinationIPOrGroupValue OBJECT-TYPE
  SYNTAX DisplayString
  ACCESS read-write
  STATUS mandatory
  DESCRIPTION
    "Variable name: OPENVPN_CONNECTION.FW_INCOMING.IN_IP
    WebUi Label: To IP
    The rule's destination IP address"
  ::= { mGuardOpenVPNFWINEntry 7 }

-- OPENVPN_CONNECTION.FW_INCOMING.IN_IP reference
mGuardOpenVPNFWINDestinationIPOrGroupRef OBJECT-TYPE
  SYNTAX OBJECT IDENTIFIER
  ACCESS read-write
  STATUS mandatory
  DESCRIPTION
    "Variable name: OPENVPN_CONNECTION.FW_INCOMING.IN_IP
    WebUi Label: To IP
    The rule's destination IP address as reference to IP group"
  ::= { mGuardOpenVPNFWINEntry 8 }

-- OPENVPN_CONNECTION.FW_INCOMING.TARGET_REF
mGuardOpenVPNFWINTargetValue OBJECT-TYPE
  SYNTAX INTEGER {
    accept(1),
    reject(2),
    drop(3)
  }
  ACCESS read-write
  STATUS mandatory
  DESCRIPTION
    "Variable name: OPENVPN_CONNECTION.FW_INCOMING.TARGET_REF
    WebUi Label: Action
    The rule's target. This object is effective if and only if the
    'mGuardOpenVPNFWINTargetRef' object contains the OID of this object."
  ::= { mGuardOpenVPNFWINEntry 15 }

-- OPENVPN_CONNECTION.FW_INCOMING.TARGET_REF reference
mGuardOpenVPNFWINTargetRef OBJECT-TYPE
  SYNTAX OBJECT IDENTIFIER
  ACCESS read-write
  STATUS mandatory
  DESCRIPTION
    "Variable name: OPENVPN_CONNECTION.FW_INCOMING.TARGET_REF
    WebUi Label: Action
    Set this object to the OID of an 'mGuardFWRuleIndex' to select a
    firewall ruleset as this rule's target. Set this object to the OID of
    the 'mGuardOpenVPNFWINTargetValue' object to choose a target from that
    objects range."
  ::= { mGuardOpenVPNFWINEntry 16 }

-- OPENVPN_CONNECTION.FW_INCOMING.IN_PORT
mGuardOpenVPNFWINDPortOrGroupValue OBJECT-TYPE
  SYNTAX DisplayString
  ACCESS read-write
  STATUS mandatory
  DESCRIPTION
    "Variable name: OPENVPN_CONNECTION.FW_INCOMING.IN_PORT
    WebUi Label: To port
    The rule's destination port"
  ::= { mGuardOpenVPNFWINEntry 11 }

-- OPENVPN_CONNECTION.FW_INCOMING.IN_PORT reference
mGuardOpenVPNFWINDPortOrGroupRef OBJECT-TYPE
  SYNTAX OBJECT IDENTIFIER
  ACCESS read-write
  STATUS mandatory
  DESCRIPTION
    "Variable name: OPENVPN_CONNECTION.FW_INCOMING.IN_PORT
    WebUi Label: To port
    The rule's destination port as reference to port group"
  ::= { mGuardOpenVPNFWINEntry 12 }

-- OPENVPN_CONNECTION.LOG_DEFAULT_INCOMING
mGuardOpenVPNConnectionFWLogDefIn OBJECT-TYPE
  SYNTAX INTEGER {
    yes(1),
    no(2)
  }
  ACCESS read-write
  STATUS mandatory
  DESCRIPTION
    "Variable name: OPENVPN_CONNECTION.LOG_DEFAULT_INCOMING
    WebUi Label: Log entries for unknown connection attempts
    Log entries for undefined incoming connection attempts."
  ::= { mGuardOpenVPNConnectionEntry 23 }

-- OPENVPN_CONNECTION.VPN_AUTH
mGuardOpenVPNConnectionAuth OBJECT-TYPE
  SYNTAX INTEGER {
    simple(1),
    x509(2),
    x509plus(3)
  }
  ACCESS read-write
  STATUS mandatory
  DESCRIPTION
    "Variable name: OPENVPN_CONNECTION.VPN_AUTH
    WebUi Label: Authentication method
    Authentication mode of the local device against the OpenVPN peer. This
    may be password authentication 'simple', certificates 'x509' or both
    methods."
  ::= { mGuardOpenVPNConnectionEntry 16 }

-- OPENVPN_CONNECTION.LOG_DEFAULT_OUTGOING
mGuardOpenVPNConnectionFWLogDefOut OBJECT-TYPE
  SYNTAX INTEGER {
    yes(1),
    no(2)
  }
  ACCESS read-write
  STATUS mandatory
  DESCRIPTION
    "Variable name: OPENVPN_CONNECTION.LOG_DEFAULT_OUTGOING
    WebUi Label: Log entries for unknown connection attempts
    Log entries for undefined outgoing connection attempts."
  ::= { mGuardOpenVPNConnectionEntry 24 }


-- OSPF_AREA table
mGuardOSPFAreaTable OBJECT-TYPE
  SYNTAX SEQUENCE OF MGuardOSPFAreaEntry
  ACCESS not-accessible
  STATUS mandatory
  DESCRIPTION
    "A table of OSPF_AREA"
  ::= { mGuardOSPF 4 }

-- OSPF_AREA table entry
mGuardOSPFAreaEntry OBJECT-TYPE
  SYNTAX MGuardOSPFAreaEntry
  ACCESS not-accessible
  STATUS mandatory
  DESCRIPTION
    "An entry of OSPF_AREA"
  INDEX { mGuardOSPFAreaIndex }
  ::= { mGuardOSPFAreaTable 1 }

MGuardOSPFAreaEntry ::= SEQUENCE {
  mGuardOSPFAreaIndex                      INTEGER,
  mGuardOSPFAreaRowStatus                  RowStatus,
  mGuardOSPFAreaName                       DisplayString,
  mGuardOSPFAreaID                         DisplayString,
  mGuardOSPFAreaStub                       INTEGER,
  mGuardOSPFAreaAuth                       INTEGER
}

-- OSPF_AREA table index
mGuardOSPFAreaIndex OBJECT-TYPE
  SYNTAX INTEGER (1..2147483647)
  ACCESS not-accessible
  STATUS mandatory
  DESCRIPTION
    "Index to OSPF_AREA"
  ::= { mGuardOSPFAreaEntry 1 }

-- OSPF_AREA row status
mGuardOSPFAreaRowStatus OBJECT-TYPE
  SYNTAX RowStatus
  ACCESS read-write
  STATUS mandatory
  DESCRIPTION
    "RowStatus of OSPF_AREA"
  ::= { mGuardOSPFAreaEntry 2 }

-- OSPF_AREA.STUB
mGuardOSPFAreaStub OBJECT-TYPE
  SYNTAX INTEGER {
    yes(1),
    no(2)
  }
  ACCESS read-write
  STATUS mandatory
  DESCRIPTION
    "Variable name: OSPF_AREA.STUB
    WebUi Label: Stub area
    Set if area ia a stub one."
  ::= { mGuardOSPFAreaEntry 5 }

-- OSPF_AREA.ID
mGuardOSPFAreaID OBJECT-TYPE
  SYNTAX DisplayString
  ACCESS read-write
  STATUS mandatory
  DESCRIPTION
    "Variable name: OSPF_AREA.ID
    WebUi Label: ID
    ID of the area in OSPF environment. This may be an IPv4 or an 32 bit
    unsigned integer value."
  ::= { mGuardOSPFAreaEntry 4 }

-- OSPF_AREA.AUTH
mGuardOSPFAreaAuth OBJECT-TYPE
  SYNTAX INTEGER {
    none(1),
    simple(2),
    digest(3)
  }
  ACCESS read-write
  STATUS mandatory
  DESCRIPTION
    "Variable name: OSPF_AREA.AUTH
    WebUi Label: Authentication
    Authentication mode used in area. This may be overridden by interface-
    based authentication."
  ::= { mGuardOSPFAreaEntry 6 }

-- OSPF_AREA.NAME
mGuardOSPFAreaName OBJECT-TYPE
  SYNTAX DisplayString
  ACCESS read-write
  STATUS mandatory
  DESCRIPTION
    "Variable name: OSPF_AREA.NAME
    WebUi Label: Name
    Name of the area, used for referencing in GUI."
  ::= { mGuardOSPFAreaEntry 3 }

-- OSPF_ENABLE
mGuardOSPFEnable OBJECT-TYPE
  SYNTAX INTEGER {
    yes(1),
    no(2)
  }
  ACCESS read-write
  STATUS mandatory
  DESCRIPTION
    "Variable name: OSPF_ENABLE
    WebUi Label: Enable OSPF
    Enable OSPF service on mGuard."
  ::= { mGuardOSPF 1 }

-- OSPF_HOSTNAME
mGuardOSPFHostname OBJECT-TYPE
  SYNTAX DisplayString
  ACCESS read-write
  STATUS mandatory
  DESCRIPTION
    "Variable name: OSPF_HOSTNAME
    WebUi Label: OSPF hostname (overrides global hostname)
    Hostname used for OSPF. This hostname can override the hostname
    configured for the system."
  ::= { mGuardOSPF 2 }


-- OSPF_INTERFACE table
mGuardOSPFInterfaceTable OBJECT-TYPE
  SYNTAX SEQUENCE OF MGuardOSPFInterfaceEntry
  ACCESS not-accessible
  STATUS mandatory
  DESCRIPTION
    "A table of OSPF_INTERFACE"
  ::= { mGuardOSPF 6 }

-- OSPF_INTERFACE table entry
mGuardOSPFInterfaceEntry OBJECT-TYPE
  SYNTAX MGuardOSPFInterfaceEntry
  ACCESS not-accessible
  STATUS mandatory
  DESCRIPTION
    "An entry of OSPF_INTERFACE"
  INDEX { mGuardOSPFInterfaceIndex }
  ::= { mGuardOSPFInterfaceTable 1 }

MGuardOSPFInterfaceEntry ::= SEQUENCE {
  mGuardOSPFInterfaceIndex                 INTEGER,
  mGuardOSPFInterfaceRowStatus             RowStatus,
  mGuardOSPFInterfaceID                    INTEGER,
  mGuardOSPFInterfacePassive               INTEGER,
  mGuardOSPFInterfaceAuth                  INTEGER,
  mGuardOSPFInterfaceSimpleKey             DisplayString,
  mGuardOSPFInterfaceDigestKey             DisplayString,
  mGuardOSPFInterfaceDigestKeyID           INTEGER
}

-- OSPF_INTERFACE table index
mGuardOSPFInterfaceIndex OBJECT-TYPE
  SYNTAX INTEGER (1..2147483647)
  ACCESS not-accessible
  STATUS mandatory
  DESCRIPTION
    "Index to OSPF_INTERFACE"
  ::= { mGuardOSPFInterfaceEntry 1 }

-- OSPF_INTERFACE row status
mGuardOSPFInterfaceRowStatus OBJECT-TYPE
  SYNTAX RowStatus
  ACCESS read-write
  STATUS mandatory
  DESCRIPTION
    "RowStatus of OSPF_INTERFACE"
  ::= { mGuardOSPFInterfaceEntry 2 }

-- OSPF_INTERFACE.DIGEST_KEY_ID
mGuardOSPFInterfaceDigestKeyID OBJECT-TYPE
  SYNTAX INTEGER(1..255)
  ACCESS read-write
  STATUS mandatory
  DESCRIPTION
    "Variable name: OSPF_INTERFACE.DIGEST_KEY_ID
    WebUi Label: Digest key ID
    Digest ID for digest based authentication."
  ::= { mGuardOSPFInterfaceEntry 8 }

-- OSPF_INTERFACE.AUTH
mGuardOSPFInterfaceAuth OBJECT-TYPE
  SYNTAX INTEGER {
    none(1),
    digest(3)
  }
  ACCESS read-write
  STATUS mandatory
  DESCRIPTION
    "Variable name: OSPF_INTERFACE.AUTH
    WebUi Label: Authentication (overrides authentication by area)
    Sets the authentication used for OSPF messages on this interface. If
    an authentication different from 'none' is set, this will override
    area based authentications."
  ::= { mGuardOSPFInterfaceEntry 5 }

-- OSPF_INTERFACE.PASSIVE
mGuardOSPFInterfacePassive OBJECT-TYPE
  SYNTAX INTEGER {
    yes(1),
    no(2)
  }
  ACCESS read-write
  STATUS mandatory
  DESCRIPTION
    "Variable name: OSPF_INTERFACE.PASSIVE
    WebUi Label: Passive interface
    Set the interface as passive. No OSPF messages will be sent out then
    there."
  ::= { mGuardOSPFInterfaceEntry 4 }

-- OSPF_INTERFACE.SIMPLE_KEY
mGuardOSPFInterfaceSimpleKey OBJECT-TYPE
  SYNTAX DisplayString
  ACCESS read-write
  STATUS mandatory
  DESCRIPTION
    "Variable name: OSPF_INTERFACE.SIMPLE_KEY
    WebUi Label: Simple authentication password
    Password for simple authentication."
  ::= { mGuardOSPFInterfaceEntry 6 }

-- OSPF_INTERFACE.ID
mGuardOSPFInterfaceID OBJECT-TYPE
  SYNTAX INTEGER {
    int(1),
    ext1(2),
    dmz(4)
  }
  ACCESS read-write
  STATUS mandatory
  DESCRIPTION
    "Variable name: OSPF_INTERFACE.ID
    WebUi Label: Interface
    ID/Name of interface on mGuard."
  ::= { mGuardOSPFInterfaceEntry 3 }

-- OSPF_INTERFACE.DIGEST_KEY
mGuardOSPFInterfaceDigestKey OBJECT-TYPE
  SYNTAX DisplayString
  ACCESS read-write
  STATUS mandatory
  DESCRIPTION
    "Variable name: OSPF_INTERFACE.DIGEST_KEY
    WebUi Label: Digest key
    Digest for digest based authentication."
  ::= { mGuardOSPFInterfaceEntry 7 }


-- OSPF_REDISTRIBUTION table
mGuardOSPFRedistributionTable OBJECT-TYPE
  SYNTAX SEQUENCE OF MGuardOSPFRedistributionEntry
  ACCESS not-accessible
  STATUS mandatory
  DESCRIPTION
    "A table of OSPF_REDISTRIBUTION"
  ::= { mGuardOSPF 5 }

-- OSPF_REDISTRIBUTION table entry
mGuardOSPFRedistributionEntry OBJECT-TYPE
  SYNTAX MGuardOSPFRedistributionEntry
  ACCESS not-accessible
  STATUS mandatory
  DESCRIPTION
    "An entry of OSPF_REDISTRIBUTION"
  INDEX { mGuardOSPFRedistributionIndex }
  ::= { mGuardOSPFRedistributionTable 1 }

MGuardOSPFRedistributionEntry ::= SEQUENCE {
  mGuardOSPFRedistributionIndex            INTEGER,
  mGuardOSPFRedistributionRowStatus        RowStatus,
  mGuardOSPFRedistributionType             INTEGER,
  mGuardOSPFRedistributionMetric           INTEGER,
  mGuardOSPFRedistributionACLValue         INTEGER,
  mGuardOSPFRedistributionACLRef           OBJECT IDENTIFIER
}

-- OSPF_REDISTRIBUTION table index
mGuardOSPFRedistributionIndex OBJECT-TYPE
  SYNTAX INTEGER (1..2147483647)
  ACCESS not-accessible
  STATUS mandatory
  DESCRIPTION
    "Index to OSPF_REDISTRIBUTION"
  ::= { mGuardOSPFRedistributionEntry 1 }

-- OSPF_REDISTRIBUTION row status
mGuardOSPFRedistributionRowStatus OBJECT-TYPE
  SYNTAX RowStatus
  ACCESS read-write
  STATUS mandatory
  DESCRIPTION
    "RowStatus of OSPF_REDISTRIBUTION"
  ::= { mGuardOSPFRedistributionEntry 2 }

-- OSPF_REDISTRIBUTION.ACCESS_LIST_REF
mGuardOSPFRedistributionACLValue OBJECT-TYPE
  SYNTAX INTEGER {
    none(1)
  }
  ACCESS read-write
  STATUS mandatory
  DESCRIPTION
    "Variable name: OSPF_REDISTRIBUTION.ACCESS_LIST_REF
    WebUi Label: Access list
    "
  ::= { mGuardOSPFRedistributionEntry 5 }

-- OSPF_REDISTRIBUTION.ACCESS_LIST_REF reference
mGuardOSPFRedistributionACLRef OBJECT-TYPE
  SYNTAX OBJECT IDENTIFIER
  ACCESS read-write
  STATUS mandatory
  DESCRIPTION
    "Variable name: OSPF_REDISTRIBUTION.ACCESS_LIST_REF
    WebUi Label: Access list
    ACLs are used to reduce the number of routes redistributed by
    redistribution rules. Set this to the OID of a
    'mGuardDynRoutingACLEntry' for filtering."
  ::= { mGuardOSPFRedistributionEntry 6 }

-- OSPF_REDISTRIBUTION.ROUTE_TYPE
mGuardOSPFRedistributionType OBJECT-TYPE
  SYNTAX INTEGER {
    connected(1),
    kernel(2)
  }
  ACCESS read-write
  STATUS mandatory
  DESCRIPTION
    "Variable name: OSPF_REDISTRIBUTION.ROUTE_TYPE
    WebUi Label: Type
    Type/Origin of routes, handled for redistribution over OSPF."
  ::= { mGuardOSPFRedistributionEntry 3 }

-- OSPF_REDISTRIBUTION.METRIC
mGuardOSPFRedistributionMetric OBJECT-TYPE
  SYNTAX INTEGER(0..16777214)
  ACCESS read-write
  STATUS mandatory
  DESCRIPTION
    "Variable name: OSPF_REDISTRIBUTION.METRIC
    WebUi Label: Metric
    Metric which should be added to routes on redistribution."
  ::= { mGuardOSPFRedistributionEntry 4 }

-- OSPF_ROUTER_ID
mGuardOSPFRouterID OBJECT-TYPE
  SYNTAX DisplayString
  ACCESS read-write
  STATUS mandatory
  DESCRIPTION
    "Variable name: OSPF_ROUTER_ID
    WebUi Label: Router ID
    Router ID of the mGuard in OSPF environment. This has to be an IPv4
    value."
  ::= { mGuardOSPF 3 }


-- PHY_SETTING table
mGuardMirrorSourceTable OBJECT-TYPE
  SYNTAX SEQUENCE OF MGuardMirrorSourceEntry
  ACCESS not-accessible
  STATUS mandatory
  DESCRIPTION
    "A table of PHY_SETTING"
  ::= { mGuardMirror 2 }

-- PHY_SETTING table entry
mGuardMirrorSourceEntry OBJECT-TYPE
  SYNTAX MGuardMirrorSourceEntry
  ACCESS not-accessible
  STATUS mandatory
  DESCRIPTION
    "An entry of PHY_SETTING"
  INDEX { mGuardMirrorSourceIndex }
  ::= { mGuardMirrorSourceTable 1 }

MGuardMirrorSourceEntry ::= SEQUENCE {
  mGuardMirrorSourceIndex                  INTEGER,
  mGuardMirrorSourceRowStatus              RowStatus,
  mGuardMirrorSource                       INTEGER
}

-- PHY_SETTING table index
mGuardMirrorSourceIndex OBJECT-TYPE
  SYNTAX INTEGER (1..2147483647)
  ACCESS not-accessible
  STATUS mandatory
  DESCRIPTION
    "Index to PHY_SETTING"
  ::= { mGuardMirrorSourceEntry 1 }

-- PHY_SETTING row status
mGuardMirrorSourceRowStatus OBJECT-TYPE
  SYNTAX RowStatus
  ACCESS read-write
  STATUS mandatory
  DESCRIPTION
    "RowStatus of PHY_SETTING"
  ::= { mGuardMirrorSourceEntry 2 }

-- PHY_SETTING.MIRROR
mGuardMirrorSource OBJECT-TYPE
  SYNTAX INTEGER {
    none(1),
    ingress(2),
    egress(3),
    both(4)
  }
  ACCESS read-write
  STATUS mandatory
  DESCRIPTION
    "Variable name: PHY_SETTING.MIRROR
    WebUi Label: Port mirroring
    Selects what packets to send from this PHY to the port mirror receiver"
  ::= { mGuardMirrorSourceEntry 3 }

-- PORT_MIRROR_RECEIVER
mGuardMirrorReceiver OBJECT-TYPE
  SYNTAX INTEGER {
    off(1),
    eth1(2),
    swp0(3),
    swp1(4),
    swp2(5),
    swp3(6),
    swp4(7)
  }
  ACCESS read-write
  STATUS mandatory
  DESCRIPTION
    "Variable name: PORT_MIRROR_RECEIVER
    WebUi Label: Port mirroring receiver
    Selects the receiver of mirrored packets"
  ::= { mGuardMirror 1 }

-- PPPOE_LOGIN
mGuardPPPOELogin OBJECT-TYPE
  SYNTAX DisplayString
  ACCESS read-write
  STATUS mandatory
  DESCRIPTION
    "Variable name: PPPOE_LOGIN
    WebUi Label: PPPoE login
    PPPoE login user name."
  ::= { mGuardPPPOE 1 }

-- PPPOE_MSS
mGuardPPPOEmss OBJECT-TYPE
  SYNTAX INTEGER
  ACCESS read-write
  STATUS mandatory
  DESCRIPTION
    "Variable name: PPPOE_MSS
    WebUi Label: TCP maximum segment size
    The maximum segment size used for PPPoE"
  ::= { mGuardPPPOE 11 }

-- PPPOE_PASSWORD
mGuardPPPOEPasswd OBJECT-TYPE
  SYNTAX DisplayString
  ACCESS read-write
  STATUS mandatory
  DESCRIPTION
    "Variable name: PPPOE_PASSWORD
    WebUi Label: PPPoE password
    PPPoE login password."
  ::= { mGuardPPPOE 2 }


-- PPPOE_PPPD_OPTIONS table
mGuardPPPOEpppdOptionsTable OBJECT-TYPE
  SYNTAX SEQUENCE OF MGuardPPPOEpppdOptionsEntry
  ACCESS not-accessible
  STATUS mandatory
  DESCRIPTION
    "A table of PPPOE_PPPD_OPTIONS"
  ::= { mGuardPPPOE 7 }

-- PPPOE_PPPD_OPTIONS table entry
mGuardPPPOEpppdOptionsEntry OBJECT-TYPE
  SYNTAX MGuardPPPOEpppdOptionsEntry
  ACCESS not-accessible
  STATUS mandatory
  DESCRIPTION
    "An entry of PPPOE_PPPD_OPTIONS"
  INDEX { mGuardPPPOEpppdOptionsIndex }
  ::= { mGuardPPPOEpppdOptionsTable 1 }

MGuardPPPOEpppdOptionsEntry ::= SEQUENCE {
  mGuardPPPOEpppdOptionsIndex              INTEGER,
  mGuardPPPOEpppdOptionsValue              DisplayString,
  mGuardPPPOEpppdOptionsRowStatus          RowStatus
}

-- PPPOE_PPPD_OPTIONS table index
mGuardPPPOEpppdOptionsIndex OBJECT-TYPE
  SYNTAX INTEGER (1..2147483647)
  ACCESS not-accessible
  STATUS mandatory
  DESCRIPTION
    "Index to PPPOE_PPPD_OPTIONS"
  ::= { mGuardPPPOEpppdOptionsEntry 1 }

-- PPPOE_PPPD_OPTIONS row status
mGuardPPPOEpppdOptionsRowStatus OBJECT-TYPE
  SYNTAX RowStatus
  ACCESS read-write
  STATUS mandatory
  DESCRIPTION
    "RowStatus of PPPOE_PPPD_OPTIONS"
  ::= { mGuardPPPOEpppdOptionsEntry 3 }

-- PPPOE_PPPD_OPTIONS.OPTION
mGuardPPPOEpppdOptionsValue OBJECT-TYPE
  SYNTAX DisplayString
  ACCESS read-write
  STATUS mandatory
  DESCRIPTION
    "Variable name: PPPOE_PPPD_OPTIONS.OPTION
    WebUi Label: Option
    The pppd option."
  ::= { mGuardPPPOEpppdOptionsEntry 2 }

-- PPPOE_RECONNECT
mGuardPPPOEReconnect OBJECT-TYPE
  SYNTAX INTEGER {
    yes(1),
    no(2)
  }
  ACCESS read-write
  STATUS mandatory
  DESCRIPTION
    "Variable name: PPPOE_RECONNECT
    WebUi Label: Automatic reconnect
    Enforce reconnection of PPPoE once a day at a certain time."
  ::= { mGuardPPPOE 8 }

-- PPPOE_RECONNECT_HOUR
mGuardPPPOEReconnectHour OBJECT-TYPE
  SYNTAX INTEGER(0..23)
  ACCESS read-write
  STATUS mandatory
  DESCRIPTION
    "Variable name: PPPOE_RECONNECT_HOUR
    WebUi Label: Reconnect daily at (hour)
    Hour of the reconnect."
  ::= { mGuardPPPOE 9 }

-- PPPOE_RECONNECT_MIN
mGuardPPPOEReconnectMin OBJECT-TYPE
  SYNTAX INTEGER(0..59)
  ACCESS read-write
  STATUS mandatory
  DESCRIPTION
    "Variable name: PPPOE_RECONNECT_MIN
    WebUi Label: Reconnect daily at (minute)
    Minute of the reconnect."
  ::= { mGuardPPPOE 10 }

-- PPPOE_SERVICE_NAME
mGuardPPPOEServiceName OBJECT-TYPE
  SYNTAX DisplayString
  ACCESS read-write
  STATUS mandatory
  DESCRIPTION
    "Variable name: PPPOE_SERVICE_NAME
    WebUi Label: PPPoE service name
    The service name used for PPPoE."
  ::= { mGuardPPPOE 4 }

-- PPPOE_USE_SERVICE_NAME
mGuardPPPOEUseServiceName OBJECT-TYPE
  SYNTAX INTEGER {
    yes(1),
    no(2)
  }
  ACCESS read-write
  STATUS mandatory
  DESCRIPTION
    "Variable name: PPPOE_USE_SERVICE_NAME
    WebUi Label: Request PPPoE service name
    Whether the PPPoE service name is used (i.e. whether it should be
    included in PPPoE PADI frames)."
  ::= { mGuardPPPOE 12 }


-- PRIVATE_CERTS table
mGuardCertsLocalTable OBJECT-TYPE
  SYNTAX SEQUENCE OF MGuardCertsLocalEntry
  ACCESS not-accessible
  STATUS mandatory
  DESCRIPTION
    "A table of PRIVATE_CERTS"
  ::= { mGuardCertsLocal 1 }

-- PRIVATE_CERTS table entry
mGuardCertsLocalEntry OBJECT-TYPE
  SYNTAX MGuardCertsLocalEntry
  ACCESS not-accessible
  STATUS mandatory
  DESCRIPTION
    "An entry of PRIVATE_CERTS"
  INDEX { mGuardCertsLocalIndex }
  ::= { mGuardCertsLocalTable 1 }

MGuardCertsLocalEntry ::= SEQUENCE {
  mGuardCertsLocalIndex                    INTEGER,
  mGuardCertsLocalName                     DisplayString,
  mGuardCertsLocalCertificate              DisplayString,
  mGuardCertsLocalPrivateKey               DisplayString,
  mGuardCertsLocalRowStatus                RowStatus
}

-- PRIVATE_CERTS table index
mGuardCertsLocalIndex OBJECT-TYPE
  SYNTAX INTEGER (1..2147483647)
  ACCESS not-accessible
  STATUS mandatory
  DESCRIPTION
    "Index to PRIVATE_CERTS"
  ::= { mGuardCertsLocalEntry 1 }

-- PRIVATE_CERTS row status
mGuardCertsLocalRowStatus OBJECT-TYPE
  SYNTAX RowStatus
  ACCESS read-write
  STATUS mandatory
  DESCRIPTION
    "RowStatus of PRIVATE_CERTS"
  ::= { mGuardCertsLocalEntry 50 }

-- PRIVATE_CERTS.FRIENDLY_NAME
mGuardCertsLocalName OBJECT-TYPE
  SYNTAX DisplayString
  ACCESS read-write
  STATUS mandatory
  DESCRIPTION
    "Variable name: PRIVATE_CERTS.FRIENDLY_NAME
    WebUi Label: Short name
    A user defined name for the certificate, which is also used to
    reference the certificate."
  ::= { mGuardCertsLocalEntry 2 }

-- PRIVATE_CERTS.CERTIFICATE
mGuardCertsLocalCertificate OBJECT-TYPE
  SYNTAX DisplayString
  ACCESS read-write
  STATUS mandatory
  DESCRIPTION
    "Variable name: PRIVATE_CERTS.CERTIFICATE
    WebUi Label: --
    The certificate."
  ::= { mGuardCertsLocalEntry 3 }

-- PRIVATE_CERTS.PRIVATEKEY
mGuardCertsLocalPrivateKey OBJECT-TYPE
  SYNTAX DisplayString
  ACCESS read-write
  STATUS mandatory
  DESCRIPTION
    "Variable name: PRIVATE_CERTS.PRIVATEKEY
    WebUi Label: --
    The certificates private key."
  ::= { mGuardCertsLocalEntry 4 }

-- PROXY_HTTP_ENABLE
mGuardProxyHTTPEnable OBJECT-TYPE
  SYNTAX INTEGER {
    yes(1),
    no(2)
  }
  ACCESS read-write
  STATUS mandatory
  DESCRIPTION
    "Variable name: PROXY_HTTP_ENABLE
    WebUi Label: Use proxy for HTTP and HTTPS (also used for VPN in TCP encapsulation)
    Use a HTTP Proxy."
  ::= { mGuardProxyHTTP 1 }

-- PROXY_HTTP_LOGIN
mGuardProxyHTTPLogin OBJECT-TYPE
  SYNTAX DisplayString
  ACCESS read-write
  STATUS mandatory
  DESCRIPTION
    "Variable name: PROXY_HTTP_LOGIN
    WebUi Label: Login
    Login for the HTTP Proxy."
  ::= { mGuardProxyHTTP 4 }

-- PROXY_HTTP_PASSWORD
mGuardProxyHTTPPassword OBJECT-TYPE
  SYNTAX DisplayString
  ACCESS read-write
  STATUS mandatory
  DESCRIPTION
    "Variable name: PROXY_HTTP_PASSWORD
    WebUi Label: Password
    Login for the HTTP Proxy."
  ::= { mGuardProxyHTTP 5 }

-- PROXY_HTTP_PORT
mGuardProxyHTTPPort OBJECT-TYPE
  SYNTAX DisplayString
  ACCESS read-write
  STATUS mandatory
  DESCRIPTION
    "Variable name: PROXY_HTTP_PORT
    WebUi Label: Port
    Port of the HTTP proxy."
  ::= { mGuardProxyHTTP 3 }

-- PROXY_HTTP_URL
mGuardProxyHTTPHost OBJECT-TYPE
  SYNTAX DisplayString
  ACCESS read-write
  STATUS mandatory
  DESCRIPTION
    "Variable name: PROXY_HTTP_URL
    WebUi Label: HTTP(S) proxy server
    Hostname or IP address of the proxy."
  ::= { mGuardProxyHTTP 2 }


-- PSM_REPOSITORIES table
mGuardUpdateServerTable OBJECT-TYPE
  SYNTAX SEQUENCE OF MGuardUpdateServerEntry
  ACCESS not-accessible
  STATUS mandatory
  DESCRIPTION
    "A table of PSM_REPOSITORIES"
  ::= { mGuardUpdate 1 }

-- PSM_REPOSITORIES table entry
mGuardUpdateServerEntry OBJECT-TYPE
  SYNTAX MGuardUpdateServerEntry
  ACCESS not-accessible
  STATUS mandatory
  DESCRIPTION
    "An entry of PSM_REPOSITORIES"
  INDEX { mGuardUpdateServerIndex }
  ::= { mGuardUpdateServerTable 1 }

MGuardUpdateServerEntry ::= SEQUENCE {
  mGuardUpdateServerIndex                  INTEGER,
  mGuardUpdateServerRowStatus              RowStatus,
  mGuardUpdateServerProto                  DisplayString,
  mGuardUpdateServerHost                   DisplayString,
  mGuardUpdateServerLogin                  DisplayString,
  mGuardUpdateServerPassword               DisplayString,
  mGuardUpdateServerPreferVPN              INTEGER
}

-- PSM_REPOSITORIES table index
mGuardUpdateServerIndex OBJECT-TYPE
  SYNTAX INTEGER (1..2147483647)
  ACCESS not-accessible
  STATUS mandatory
  DESCRIPTION
    "Index to PSM_REPOSITORIES"
  ::= { mGuardUpdateServerEntry 1 }

-- PSM_REPOSITORIES row status
mGuardUpdateServerRowStatus OBJECT-TYPE
  SYNTAX RowStatus
  ACCESS read-write
  STATUS mandatory
  DESCRIPTION
    "RowStatus of PSM_REPOSITORIES"
  ::= { mGuardUpdateServerEntry 3 }

-- PSM_REPOSITORIES.PREFER_VPN
mGuardUpdateServerPreferVPN OBJECT-TYPE
  SYNTAX INTEGER {
    yes(1),
    no(2)
  }
  ACCESS read-write
  STATUS mandatory
  DESCRIPTION
    "Variable name: PSM_REPOSITORIES.PREFER_VPN
    WebUi Label: Via VPN
    Connect to Update server via VPN if an applicable tunnel is
    configured. Important note: If set to 'yes', all proxy settings are
    ignored and no proxy will be used even if no applicable VPN tunnel
    exists! The server will then be connected directly."
  ::= { mGuardUpdateServerEntry 8 }

-- PSM_REPOSITORIES.LOGIN
mGuardUpdateServerLogin OBJECT-TYPE
  SYNTAX DisplayString
  ACCESS read-write
  STATUS mandatory
  DESCRIPTION
    "Variable name: PSM_REPOSITORIES.LOGIN
    WebUi Label: Login
    Login on the update server."
  ::= { mGuardUpdateServerEntry 6 }

-- PSM_REPOSITORIES.PASSWORD
mGuardUpdateServerPassword OBJECT-TYPE
  SYNTAX DisplayString
  ACCESS read-write
  STATUS mandatory
  DESCRIPTION
    "Variable name: PSM_REPOSITORIES.PASSWORD
    WebUi Label: Password
    Password on the update server."
  ::= { mGuardUpdateServerEntry 7 }

-- PSM_REPOSITORIES.SERVER
mGuardUpdateServerHost OBJECT-TYPE
  SYNTAX DisplayString
  ACCESS read-write
  STATUS mandatory
  DESCRIPTION
    "Variable name: PSM_REPOSITORIES.SERVER
    WebUi Label: Server
    Hostname or IP address of the update server."
  ::= { mGuardUpdateServerEntry 5 }

-- PSM_REPOSITORIES.PROTO
mGuardUpdateServerProto OBJECT-TYPE
  SYNTAX DisplayString
  ACCESS read-write
  STATUS mandatory
  DESCRIPTION
    "Variable name: PSM_REPOSITORIES.PROTO
    WebUi Label: Protocol
    Protocol, either https, http, ftp, or tftp"
  ::= { mGuardUpdateServerEntry 4 }

-- QOS_EGRESS_DIALIN_DEFAULT reference
mGuardQoSEgDialinDefaultQueueRef OBJECT-TYPE
  SYNTAX OBJECT IDENTIFIER
  ACCESS read-write
  STATUS mandatory
  DESCRIPTION
    "Variable name: QOS_EGRESS_DIALIN_DEFAULT
    WebUi Label: Default queue
    When this object contains the OID of an 'mGuardQoSEgDialinQuIndex'
    object, the corresponding QoS Egress dial-in queue is used as default
    queue."
  ::= { mGuardQoSEgDialin 7 }

-- QOS_EGRESS_DIALIN_ENABLE
mGuardQoSEgDialinEnable OBJECT-TYPE
  SYNTAX INTEGER {
    yes(1),
    no(2)
  }
  ACCESS read-write
  STATUS mandatory
  DESCRIPTION
    "Variable name: QOS_EGRESS_DIALIN_ENABLE
    WebUi Label: Enable Egress QoS
    Enable egress QoS queuing."
  ::= { mGuardQoSEgDialin 1 }


-- QOS_EGRESS_DIALIN_QUEUES table
mGuardQoSEgDialinQueueTable OBJECT-TYPE
  SYNTAX SEQUENCE OF MGuardQoSEgDialinQueueEntry
  ACCESS not-accessible
  STATUS mandatory
  DESCRIPTION
    "A table of QOS_EGRESS_DIALIN_QUEUES"
  ::= { mGuardQoSEgDialin 4 }

-- QOS_EGRESS_DIALIN_QUEUES table entry
mGuardQoSEgDialinQueueEntry OBJECT-TYPE
  SYNTAX MGuardQoSEgDialinQueueEntry
  ACCESS not-accessible
  STATUS mandatory
  DESCRIPTION
    "An entry of QOS_EGRESS_DIALIN_QUEUES"
  INDEX { mGuardQoSEgDialinQuIndex }
  ::= { mGuardQoSEgDialinQueueTable 1 }

MGuardQoSEgDialinQueueEntry ::= SEQUENCE {
  mGuardQoSEgDialinQuIndex                 INTEGER,
  mGuardQoSEgDialinQuName                  DisplayString,
  mGuardQoSEgDialinQuMinRate               DisplayString,
  mGuardQoSEgDialinQuMaxRate               DisplayString,
  mGuardQoSEgDialinQuPref                  INTEGER,
  mGuardQoSEgDialinQuComment               DisplayString,
  mGuardQoSEgDialinQuRowStatus             RowStatus
}

-- QOS_EGRESS_DIALIN_QUEUES table index
mGuardQoSEgDialinQuIndex OBJECT-TYPE
  SYNTAX INTEGER (1..2147483647)
  ACCESS not-accessible
  STATUS mandatory
  DESCRIPTION
    "Index to QOS_EGRESS_DIALIN_QUEUES"
  ::= { mGuardQoSEgDialinQueueEntry 1 }

-- QOS_EGRESS_DIALIN_QUEUES row status
mGuardQoSEgDialinQuRowStatus OBJECT-TYPE
  SYNTAX RowStatus
  ACCESS read-write
  STATUS mandatory
  DESCRIPTION
    "RowStatus of QOS_EGRESS_DIALIN_QUEUES"
  ::= { mGuardQoSEgDialinQueueEntry 7 }

-- QOS_EGRESS_DIALIN_QUEUES.COMMENT
mGuardQoSEgDialinQuComment OBJECT-TYPE
  SYNTAX DisplayString
  ACCESS read-write
  STATUS mandatory
  DESCRIPTION
    "Variable name: QOS_EGRESS_DIALIN_QUEUES.COMMENT
    WebUi Label: Comment
    Comment."
  ::= { mGuardQoSEgDialinQueueEntry 6 }

-- QOS_EGRESS_DIALIN_QUEUES.MIN_RATE
mGuardQoSEgDialinQuMinRate OBJECT-TYPE
  SYNTAX DisplayString
  ACCESS read-write
  STATUS mandatory
  DESCRIPTION
    "Variable name: QOS_EGRESS_DIALIN_QUEUES.MIN_RATE
    WebUi Label: Guaranteed
    Guaranteed rate: >=1 or 'unlimited'."
  ::= { mGuardQoSEgDialinQueueEntry 3 }

-- QOS_EGRESS_DIALIN_QUEUES.MAX_RATE
mGuardQoSEgDialinQuMaxRate OBJECT-TYPE
  SYNTAX DisplayString
  ACCESS read-write
  STATUS mandatory
  DESCRIPTION
    "Variable name: QOS_EGRESS_DIALIN_QUEUES.MAX_RATE
    WebUi Label: Upper limit
    Guaranteed rate: >=1 or 'unlimited'."
  ::= { mGuardQoSEgDialinQueueEntry 4 }

-- QOS_EGRESS_DIALIN_QUEUES.NAME
mGuardQoSEgDialinQuName OBJECT-TYPE
  SYNTAX DisplayString
  ACCESS read-write
  STATUS mandatory
  DESCRIPTION
    "Variable name: QOS_EGRESS_DIALIN_QUEUES.NAME
    WebUi Label: Name
    Name of the queue."
  ::= { mGuardQoSEgDialinQueueEntry 2 }

-- QOS_EGRESS_DIALIN_QUEUES.PREFERENCE
mGuardQoSEgDialinQuPref OBJECT-TYPE
  SYNTAX INTEGER {
    low(1),
    medium(2),
    high(3)
  }
  ACCESS read-write
  STATUS mandatory
  DESCRIPTION
    "Variable name: QOS_EGRESS_DIALIN_QUEUES.PREFERENCE
    WebUi Label: Priority
    Preference of queue."
  ::= { mGuardQoSEgDialinQueueEntry 5 }

-- QOS_EGRESS_DIALIN_RATE
mGuardQoSEgDialinRate OBJECT-TYPE
  SYNTAX DisplayString
  ACCESS read-write
  STATUS mandatory
  DESCRIPTION
    "Variable name: QOS_EGRESS_DIALIN_RATE
    WebUi Label: Bandwidth
    Rate for egress QoS management: number >= 1 or 'unlimited'."
  ::= { mGuardQoSEgDialin 3 }


-- QOS_EGRESS_DIALIN_RULES table
mGuardQoSEgDialinRuleTable OBJECT-TYPE
  SYNTAX SEQUENCE OF MGuardQoSEgDialinRuleEntry
  ACCESS not-accessible
  STATUS mandatory
  DESCRIPTION
    "A table of QOS_EGRESS_DIALIN_RULES"
  ::= { mGuardQoSEgDialin 6 }

-- QOS_EGRESS_DIALIN_RULES table entry
mGuardQoSEgDialinRuleEntry OBJECT-TYPE
  SYNTAX MGuardQoSEgDialinRuleEntry
  ACCESS not-accessible
  STATUS mandatory
  DESCRIPTION
    "An entry of QOS_EGRESS_DIALIN_RULES"
  INDEX { mGuardQoSEgDialinRuIndex }
  ::= { mGuardQoSEgDialinRuleTable 1 }

MGuardQoSEgDialinRuleEntry ::= SEQUENCE {
  mGuardQoSEgDialinRuIndex                 INTEGER,
  mGuardQoSEgDialinRuProto                 INTEGER,
  mGuardQoSEgDialinRuSourceIP              DisplayString,
  mGuardQoSEgDialinRuSport                 DisplayString,
  mGuardQoSEgDialinRuDestIP                DisplayString,
  mGuardQoSEgDialinRuDport                 DisplayString,
  mGuardQoSEgDialinRuFindDSCP              INTEGER,
  mGuardQoSEgDialinRuSetDSCP               INTEGER,
  mGuardQoSEgDialinRuComment               DisplayString,
  mGuardQoSEgDialinRuRowStatus             RowStatus,
  mGuardQoSEgDialinRuQRef                  OBJECT IDENTIFIER
}

-- QOS_EGRESS_DIALIN_RULES table index
mGuardQoSEgDialinRuIndex OBJECT-TYPE
  SYNTAX INTEGER (1..2147483647)
  ACCESS not-accessible
  STATUS mandatory
  DESCRIPTION
    "Index to QOS_EGRESS_DIALIN_RULES"
  ::= { mGuardQoSEgDialinRuleEntry 1 }

-- QOS_EGRESS_DIALIN_RULES row status
mGuardQoSEgDialinRuRowStatus OBJECT-TYPE
  SYNTAX RowStatus
  ACCESS read-write
  STATUS mandatory
  DESCRIPTION
    "RowStatus of QOS_EGRESS_DIALIN_RULES"
  ::= { mGuardQoSEgDialinRuleEntry 11 }

-- QOS_EGRESS_DIALIN_RULES.COMMENT
mGuardQoSEgDialinRuComment OBJECT-TYPE
  SYNTAX DisplayString
  ACCESS read-write
  STATUS mandatory
  DESCRIPTION
    "Variable name: QOS_EGRESS_DIALIN_RULES.COMMENT
    WebUi Label: Comment
    Comment."
  ::= { mGuardQoSEgDialinRuleEntry 10 }

-- QOS_EGRESS_DIALIN_RULES.FROM_PORT
mGuardQoSEgDialinRuSport OBJECT-TYPE
  SYNTAX DisplayString
  ACCESS read-write
  STATUS mandatory
  DESCRIPTION
    "Variable name: QOS_EGRESS_DIALIN_RULES.FROM_PORT
    WebUi Label: From port
    The rule's source port"
  ::= { mGuardQoSEgDialinRuleEntry 4 }

-- QOS_EGRESS_DIALIN_RULES.PROTO
mGuardQoSEgDialinRuProto OBJECT-TYPE
  SYNTAX INTEGER {
    icmp(1),
    tcp(6),
    udp(17),
    esp(50),
    all(256)
  }
  ACCESS read-write
  STATUS mandatory
  DESCRIPTION
    "Variable name: QOS_EGRESS_DIALIN_RULES.PROTO
    WebUi Label: Protocol
    The rule's protocol"
  ::= { mGuardQoSEgDialinRuleEntry 2 }

-- QOS_EGRESS_DIALIN_RULES.SET_TOSDSCP
mGuardQoSEgDialinRuSetDSCP OBJECT-TYPE
  SYNTAX INTEGER {
    tos-normal-service(100),
    tos-minimize-delay(101),
    tos-maximize-throughput(102),
    tos-maximize-reliability(103),
    tos-minimize-cost(104),
    dscp-class-be(200),
    dscp-class-ef(201),
    dscp-class-af11(202),
    dscp-class-af12(203),
    dscp-class-af13(204),
    dscp-class-af21(205),
    dscp-class-af22(206),
    dscp-class-af23(207),
    dscp-class-af31(208),
    dscp-class-af32(209),
    dscp-class-af33(210),
    dscp-class-af41(211),
    dscp-class-af42(212),
    dscp-class-af43(213),
    dscp-class-cs0(300),
    dscp-class-cs1(301),
    dscp-class-cs2(302),
    dscp-class-cs3(303),
    dscp-class-cs4(304),
    dscp-class-cs5(305),
    dscp-class-cs6(306),
    dscp-class-cs7(307),
    dscp-value-0x00(400),
    dscp-value-0x01(401),
    dscp-value-0x02(402),
    dscp-value-0x03(403),
    dscp-value-0x04(404),
    dscp-value-0x05(405),
    dscp-value-0x06(406),
    dscp-value-0x07(407),
    dscp-value-0x08(408),
    dscp-value-0x09(409),
    dscp-value-0x0a(410),
    dscp-value-0x0b(411),
    dscp-value-0x0c(412),
    dscp-value-0x0d(413),
    dscp-value-0x0e(414),
    dscp-value-0x0f(415),
    dscp-value-0x10(416),
    dscp-value-0x11(417),
    dscp-value-0x12(418),
    dscp-value-0x13(419),
    dscp-value-0x14(420),
    dscp-value-0x15(421),
    dscp-value-0x16(422),
    dscp-value-0x17(423),
    dscp-value-0x18(424),
    dscp-value-0x19(425),
    dscp-value-0x1a(426),
    dscp-value-0x1b(427),
    dscp-value-0x1c(428),
    dscp-value-0x1d(429),
    dscp-value-0x1e(430),
    dscp-value-0x1f(431),
    dscp-value-0x20(432),
    dscp-value-0x21(433),
    dscp-value-0x22(434),
    dscp-value-0x23(435),
    dscp-value-0x24(436),
    dscp-value-0x25(437),
    dscp-value-0x26(438),
    dscp-value-0x27(439),
    dscp-value-0x28(440),
    dscp-value-0x29(441),
    dscp-value-0x2a(442),
    dscp-value-0x2b(443),
    dscp-value-0x2c(444),
    dscp-value-0x2d(445),
    dscp-value-0x2e(446),
    dscp-value-0x2f(447),
    dscp-value-0x30(448),
    dscp-value-0x31(449),
    dscp-value-0x32(450),
    dscp-value-0x33(451),
    dscp-value-0x34(452),
    dscp-value-0x35(453),
    dscp-value-0x36(454),
    dscp-value-0x37(455),
    dscp-value-0x38(456),
    dscp-value-0x39(457),
    dscp-value-0x3a(458),
    dscp-value-0x3b(459),
    dscp-value-0x3c(460),
    dscp-value-0x3d(461),
    dscp-value-0x3e(462),
    dscp-value-0x3f(463),
    unchanged(2000)
  }
  ACCESS read-write
  STATUS mandatory
  DESCRIPTION
    "Variable name: QOS_EGRESS_DIALIN_RULES.SET_TOSDSCP
    WebUi Label: New TOS/DSCP
    The rule's target for the DSCP/TOS field"
  ::= { mGuardQoSEgDialinRuleEntry 8 }

-- QOS_EGRESS_DIALIN_RULES.FROM_IP
mGuardQoSEgDialinRuSourceIP OBJECT-TYPE
  SYNTAX DisplayString
  ACCESS read-write
  STATUS mandatory
  DESCRIPTION
    "Variable name: QOS_EGRESS_DIALIN_RULES.FROM_IP
    WebUi Label: From IP
    The rule's source IP address"
  ::= { mGuardQoSEgDialinRuleEntry 3 }

-- QOS_EGRESS_DIALIN_RULES.IN_IP
mGuardQoSEgDialinRuDestIP OBJECT-TYPE
  SYNTAX DisplayString
  ACCESS read-write
  STATUS mandatory
  DESCRIPTION
    "Variable name: QOS_EGRESS_DIALIN_RULES.IN_IP
    WebUi Label: To IP
    The rule's destination IP address"
  ::= { mGuardQoSEgDialinRuleEntry 5 }

-- QOS_EGRESS_DIALIN_RULES.QUEUE reference
mGuardQoSEgDialinRuQRef OBJECT-TYPE
  SYNTAX OBJECT IDENTIFIER
  ACCESS read-write
  STATUS mandatory
  DESCRIPTION
    "Variable name: QOS_EGRESS_DIALIN_RULES.QUEUE
    WebUi Label: Queue name
    When this object contains the OID of an 'mGuardQoSEgDialinQuIndex'
    object, the corresponding QoS Egress dial-in queue is used as the
    rule's target queue."
  ::= { mGuardQoSEgDialinRuleEntry 12 }

-- QOS_EGRESS_DIALIN_RULES.FIND_TOSDSCP
mGuardQoSEgDialinRuFindDSCP OBJECT-TYPE
  SYNTAX INTEGER {
    tos-normal-service(100),
    tos-minimize-delay(101),
    tos-maximize-throughput(102),
    tos-maximize-reliability(103),
    tos-minimize-cost(104),
    dscp-class-be(200),
    dscp-class-ef(201),
    dscp-class-af11(202),
    dscp-class-af12(203),
    dscp-class-af13(204),
    dscp-class-af21(205),
    dscp-class-af22(206),
    dscp-class-af23(207),
    dscp-class-af31(208),
    dscp-class-af32(209),
    dscp-class-af33(210),
    dscp-class-af41(211),
    dscp-class-af42(212),
    dscp-class-af43(213),
    dscp-class-cs0(300),
    dscp-class-cs1(301),
    dscp-class-cs2(302),
    dscp-class-cs3(303),
    dscp-class-cs4(304),
    dscp-class-cs5(305),
    dscp-class-cs6(306),
    dscp-class-cs7(307),
    dscp-value-0x00(400),
    dscp-value-0x01(401),
    dscp-value-0x02(402),
    dscp-value-0x03(403),
    dscp-value-0x04(404),
    dscp-value-0x05(405),
    dscp-value-0x06(406),
    dscp-value-0x07(407),
    dscp-value-0x08(408),
    dscp-value-0x09(409),
    dscp-value-0x0a(410),
    dscp-value-0x0b(411),
    dscp-value-0x0c(412),
    dscp-value-0x0d(413),
    dscp-value-0x0e(414),
    dscp-value-0x0f(415),
    dscp-value-0x10(416),
    dscp-value-0x11(417),
    dscp-value-0x12(418),
    dscp-value-0x13(419),
    dscp-value-0x14(420),
    dscp-value-0x15(421),
    dscp-value-0x16(422),
    dscp-value-0x17(423),
    dscp-value-0x18(424),
    dscp-value-0x19(425),
    dscp-value-0x1a(426),
    dscp-value-0x1b(427),
    dscp-value-0x1c(428),
    dscp-value-0x1d(429),
    dscp-value-0x1e(430),
    dscp-value-0x1f(431),
    dscp-value-0x20(432),
    dscp-value-0x21(433),
    dscp-value-0x22(434),
    dscp-value-0x23(435),
    dscp-value-0x24(436),
    dscp-value-0x25(437),
    dscp-value-0x26(438),
    dscp-value-0x27(439),
    dscp-value-0x28(440),
    dscp-value-0x29(441),
    dscp-value-0x2a(442),
    dscp-value-0x2b(443),
    dscp-value-0x2c(444),
    dscp-value-0x2d(445),
    dscp-value-0x2e(446),
    dscp-value-0x2f(447),
    dscp-value-0x30(448),
    dscp-value-0x31(449),
    dscp-value-0x32(450),
    dscp-value-0x33(451),
    dscp-value-0x34(452),
    dscp-value-0x35(453),
    dscp-value-0x36(454),
    dscp-value-0x37(455),
    dscp-value-0x38(456),
    dscp-value-0x39(457),
    dscp-value-0x3a(458),
    dscp-value-0x3b(459),
    dscp-value-0x3c(460),
    dscp-value-0x3d(461),
    dscp-value-0x3e(462),
    dscp-value-0x3f(463),
    all(1000),
    tos-not-normal-service(1001),
    dscp-class-not-be(1002),
    dscp-class-not-cs0(1003),
    dscp-value-not-0(1004)
  }
  ACCESS read-write
  STATUS mandatory
  DESCRIPTION
    "Variable name: QOS_EGRESS_DIALIN_RULES.FIND_TOSDSCP
    WebUi Label: Current TOS/DSCP
    The rule's match on the DSCP/TOS field"
  ::= { mGuardQoSEgDialinRuleEntry 7 }

-- QOS_EGRESS_DIALIN_RULES.IN_PORT
mGuardQoSEgDialinRuDport OBJECT-TYPE
  SYNTAX DisplayString
  ACCESS read-write
  STATUS mandatory
  DESCRIPTION
    "Variable name: QOS_EGRESS_DIALIN_RULES.IN_PORT
    WebUi Label: To port
    The rule's destination port"
  ::= { mGuardQoSEgDialinRuleEntry 6 }

-- QOS_EGRESS_DIALIN_UNIT
mGuardQoSEgDialinUnit OBJECT-TYPE
  SYNTAX INTEGER {
    kbitpersec(1),
    packetpersec(2)
  }
  ACCESS read-write
  STATUS mandatory
  DESCRIPTION
    "Variable name: QOS_EGRESS_DIALIN_UNIT
    WebUi Label: Measurement unit
    Unit for egress QoS management."
  ::= { mGuardQoSEgDialin 2 }

-- QOS_EGRESS_DIALIN_VPN_DEFAULT reference
mGuardQoSEgVPNDialinDefaultQRef OBJECT-TYPE
  SYNTAX OBJECT IDENTIFIER
  ACCESS read-write
  STATUS mandatory
  DESCRIPTION
    "Variable name: QOS_EGRESS_DIALIN_VPN_DEFAULT
    WebUi Label: Default queue
    When this object contains the OID of an 'mGuardQoSEgVPNDialinQuIndex'
    object, the corresponding QoS Egress VPN dial-in queue is used as
    default queue."
  ::= { mGuardQoSEgVPNDialin 7 }

-- QOS_EGRESS_DIALIN_VPN_ENABLE
mGuardQoSEgVPNDialinEnable OBJECT-TYPE
  SYNTAX INTEGER {
    yes(1),
    no(2)
  }
  ACCESS read-write
  STATUS mandatory
  DESCRIPTION
    "Variable name: QOS_EGRESS_DIALIN_VPN_ENABLE
    WebUi Label: Enable Egress QoS
    Enable egress QoS queuing."
  ::= { mGuardQoSEgVPNDialin 1 }


-- QOS_EGRESS_DIALIN_VPN_QUEUES table
mGuardQoSEgVPNDialinQueueTable OBJECT-TYPE
  SYNTAX SEQUENCE OF MGuardQoSEgVPNDialinQueueEntry
  ACCESS not-accessible
  STATUS mandatory
  DESCRIPTION
    "A table of QOS_EGRESS_DIALIN_VPN_QUEUES"
  ::= { mGuardQoSEgVPNDialin 4 }

-- QOS_EGRESS_DIALIN_VPN_QUEUES table entry
mGuardQoSEgVPNDialinQueueEntry OBJECT-TYPE
  SYNTAX MGuardQoSEgVPNDialinQueueEntry
  ACCESS not-accessible
  STATUS mandatory
  DESCRIPTION
    "An entry of QOS_EGRESS_DIALIN_VPN_QUEUES"
  INDEX { mGuardQoSEgVPNDialinQuIndex }
  ::= { mGuardQoSEgVPNDialinQueueTable 1 }

MGuardQoSEgVPNDialinQueueEntry ::= SEQUENCE {
  mGuardQoSEgVPNDialinQuIndex              INTEGER,
  mGuardQoSEgVPNDialinQuName               DisplayString,
  mGuardQoSEgVPNDialinQuMinRate            DisplayString,
  mGuardQoSEgVPNDialinQuMaxRate            DisplayString,
  mGuardQoSEgVPNDialinQuPref               INTEGER,
  mGuardQoSEgVPNDialinQuComment            DisplayString,
  mGuardQoSEgVPNDialinQuRowStatus          RowStatus
}

-- QOS_EGRESS_DIALIN_VPN_QUEUES table index
mGuardQoSEgVPNDialinQuIndex OBJECT-TYPE
  SYNTAX INTEGER (1..2147483647)
  ACCESS not-accessible
  STATUS mandatory
  DESCRIPTION
    "Index to QOS_EGRESS_DIALIN_VPN_QUEUES"
  ::= { mGuardQoSEgVPNDialinQueueEntry 1 }

-- QOS_EGRESS_DIALIN_VPN_QUEUES row status
mGuardQoSEgVPNDialinQuRowStatus OBJECT-TYPE
  SYNTAX RowStatus
  ACCESS read-write
  STATUS mandatory
  DESCRIPTION
    "RowStatus of QOS_EGRESS_DIALIN_VPN_QUEUES"
  ::= { mGuardQoSEgVPNDialinQueueEntry 7 }

-- QOS_EGRESS_DIALIN_VPN_QUEUES.COMMENT
mGuardQoSEgVPNDialinQuComment OBJECT-TYPE
  SYNTAX DisplayString
  ACCESS read-write
  STATUS mandatory
  DESCRIPTION
    "Variable name: QOS_EGRESS_DIALIN_VPN_QUEUES.COMMENT
    WebUi Label: Comment
    Comment."
  ::= { mGuardQoSEgVPNDialinQueueEntry 6 }

-- QOS_EGRESS_DIALIN_VPN_QUEUES.MIN_RATE
mGuardQoSEgVPNDialinQuMinRate OBJECT-TYPE
  SYNTAX DisplayString
  ACCESS read-write
  STATUS mandatory
  DESCRIPTION
    "Variable name: QOS_EGRESS_DIALIN_VPN_QUEUES.MIN_RATE
    WebUi Label: Guaranteed
    Guaranteed rate: >=1 or 'unlimited'."
  ::= { mGuardQoSEgVPNDialinQueueEntry 3 }

-- QOS_EGRESS_DIALIN_VPN_QUEUES.MAX_RATE
mGuardQoSEgVPNDialinQuMaxRate OBJECT-TYPE
  SYNTAX DisplayString
  ACCESS read-write
  STATUS mandatory
  DESCRIPTION
    "Variable name: QOS_EGRESS_DIALIN_VPN_QUEUES.MAX_RATE
    WebUi Label: Upper limit
    Guaranteed rate: >=1 or 'unlimited'."
  ::= { mGuardQoSEgVPNDialinQueueEntry 4 }

-- QOS_EGRESS_DIALIN_VPN_QUEUES.NAME
mGuardQoSEgVPNDialinQuName OBJECT-TYPE
  SYNTAX DisplayString
  ACCESS read-write
  STATUS mandatory
  DESCRIPTION
    "Variable name: QOS_EGRESS_DIALIN_VPN_QUEUES.NAME
    WebUi Label: Name
    Name of the queue."
  ::= { mGuardQoSEgVPNDialinQueueEntry 2 }

-- QOS_EGRESS_DIALIN_VPN_QUEUES.PREFERENCE
mGuardQoSEgVPNDialinQuPref OBJECT-TYPE
  SYNTAX INTEGER {
    low(1),
    medium(2),
    high(3)
  }
  ACCESS read-write
  STATUS mandatory
  DESCRIPTION
    "Variable name: QOS_EGRESS_DIALIN_VPN_QUEUES.PREFERENCE
    WebUi Label: Priority
    Preference of queue."
  ::= { mGuardQoSEgVPNDialinQueueEntry 5 }

-- QOS_EGRESS_DIALIN_VPN_RATE
mGuardQoSEgVPNDialinRate OBJECT-TYPE
  SYNTAX DisplayString
  ACCESS read-write
  STATUS mandatory
  DESCRIPTION
    "Variable name: QOS_EGRESS_DIALIN_VPN_RATE
    WebUi Label: Bandwidth
    Rate for egress QoS management: number >= 1 or 'unlimited'."
  ::= { mGuardQoSEgVPNDialin 3 }


-- QOS_EGRESS_DIALIN_VPN_RULES table
mGuardQoSEgVPNDialinRuleTable OBJECT-TYPE
  SYNTAX SEQUENCE OF MGuardQoSEgVPNDialinRuleEntry
  ACCESS not-accessible
  STATUS mandatory
  DESCRIPTION
    "A table of QOS_EGRESS_DIALIN_VPN_RULES"
  ::= { mGuardQoSEgVPNDialin 6 }

-- QOS_EGRESS_DIALIN_VPN_RULES table entry
mGuardQoSEgVPNDialinRuleEntry OBJECT-TYPE
  SYNTAX MGuardQoSEgVPNDialinRuleEntry
  ACCESS not-accessible
  STATUS mandatory
  DESCRIPTION
    "An entry of QOS_EGRESS_DIALIN_VPN_RULES"
  INDEX { mGuardQoSEgVPNDialinRuIndex }
  ::= { mGuardQoSEgVPNDialinRuleTable 1 }

MGuardQoSEgVPNDialinRuleEntry ::= SEQUENCE {
  mGuardQoSEgVPNDialinRuIndex              INTEGER,
  mGuardQoSEgVPNDialinRuProto              INTEGER,
  mGuardQoSEgVPNDialinRuSourceIP           DisplayString,
  mGuardQoSEgVPNDialinRuSport              DisplayString,
  mGuardQoSEgVPNDialinRuDestIP             DisplayString,
  mGuardQoSEgVPNDialinRuDport              DisplayString,
  mGuardQoSEgVPNDialinRuFindDSCP           INTEGER,
  mGuardQoSEgVPNDialinRuSetDSCP            INTEGER,
  mGuardQoSEgVPNDialinRuComment            DisplayString,
  mGuardQoSEgVPNDialinRuRowStatus          RowStatus,
  mGuardQoSEgVPNDialinRuQRef               OBJECT IDENTIFIER
}

-- QOS_EGRESS_DIALIN_VPN_RULES table index
mGuardQoSEgVPNDialinRuIndex OBJECT-TYPE
  SYNTAX INTEGER (1..2147483647)
  ACCESS not-accessible
  STATUS mandatory
  DESCRIPTION
    "Index to QOS_EGRESS_DIALIN_VPN_RULES"
  ::= { mGuardQoSEgVPNDialinRuleEntry 1 }

-- QOS_EGRESS_DIALIN_VPN_RULES row status
mGuardQoSEgVPNDialinRuRowStatus OBJECT-TYPE
  SYNTAX RowStatus
  ACCESS read-write
  STATUS mandatory
  DESCRIPTION
    "RowStatus of QOS_EGRESS_DIALIN_VPN_RULES"
  ::= { mGuardQoSEgVPNDialinRuleEntry 11 }

-- QOS_EGRESS_DIALIN_VPN_RULES.COMMENT
mGuardQoSEgVPNDialinRuComment OBJECT-TYPE
  SYNTAX DisplayString
  ACCESS read-write
  STATUS mandatory
  DESCRIPTION
    "Variable name: QOS_EGRESS_DIALIN_VPN_RULES.COMMENT
    WebUi Label: Comment
    Comment."
  ::= { mGuardQoSEgVPNDialinRuleEntry 10 }

-- QOS_EGRESS_DIALIN_VPN_RULES.FROM_PORT
mGuardQoSEgVPNDialinRuSport OBJECT-TYPE
  SYNTAX DisplayString
  ACCESS read-write
  STATUS mandatory
  DESCRIPTION
    "Variable name: QOS_EGRESS_DIALIN_VPN_RULES.FROM_PORT
    WebUi Label: From port
    The rule's source port"
  ::= { mGuardQoSEgVPNDialinRuleEntry 4 }

-- QOS_EGRESS_DIALIN_VPN_RULES.PROTO
mGuardQoSEgVPNDialinRuProto OBJECT-TYPE
  SYNTAX INTEGER {
    icmp(1),
    tcp(6),
    udp(17),
    esp(50),
    all(256)
  }
  ACCESS read-write
  STATUS mandatory
  DESCRIPTION
    "Variable name: QOS_EGRESS_DIALIN_VPN_RULES.PROTO
    WebUi Label: Protocol
    The rule's protocol"
  ::= { mGuardQoSEgVPNDialinRuleEntry 2 }

-- QOS_EGRESS_DIALIN_VPN_RULES.SET_TOSDSCP
mGuardQoSEgVPNDialinRuSetDSCP OBJECT-TYPE
  SYNTAX INTEGER {
    tos-normal-service(100),
    tos-minimize-delay(101),
    tos-maximize-throughput(102),
    tos-maximize-reliability(103),
    tos-minimize-cost(104),
    dscp-class-be(200),
    dscp-class-ef(201),
    dscp-class-af11(202),
    dscp-class-af12(203),
    dscp-class-af13(204),
    dscp-class-af21(205),
    dscp-class-af22(206),
    dscp-class-af23(207),
    dscp-class-af31(208),
    dscp-class-af32(209),
    dscp-class-af33(210),
    dscp-class-af41(211),
    dscp-class-af42(212),
    dscp-class-af43(213),
    dscp-class-cs0(300),
    dscp-class-cs1(301),
    dscp-class-cs2(302),
    dscp-class-cs3(303),
    dscp-class-cs4(304),
    dscp-class-cs5(305),
    dscp-class-cs6(306),
    dscp-class-cs7(307),
    dscp-value-0x00(400),
    dscp-value-0x01(401),
    dscp-value-0x02(402),
    dscp-value-0x03(403),
    dscp-value-0x04(404),
    dscp-value-0x05(405),
    dscp-value-0x06(406),
    dscp-value-0x07(407),
    dscp-value-0x08(408),
    dscp-value-0x09(409),
    dscp-value-0x0a(410),
    dscp-value-0x0b(411),
    dscp-value-0x0c(412),
    dscp-value-0x0d(413),
    dscp-value-0x0e(414),
    dscp-value-0x0f(415),
    dscp-value-0x10(416),
    dscp-value-0x11(417),
    dscp-value-0x12(418),
    dscp-value-0x13(419),
    dscp-value-0x14(420),
    dscp-value-0x15(421),
    dscp-value-0x16(422),
    dscp-value-0x17(423),
    dscp-value-0x18(424),
    dscp-value-0x19(425),
    dscp-value-0x1a(426),
    dscp-value-0x1b(427),
    dscp-value-0x1c(428),
    dscp-value-0x1d(429),
    dscp-value-0x1e(430),
    dscp-value-0x1f(431),
    dscp-value-0x20(432),
    dscp-value-0x21(433),
    dscp-value-0x22(434),
    dscp-value-0x23(435),
    dscp-value-0x24(436),
    dscp-value-0x25(437),
    dscp-value-0x26(438),
    dscp-value-0x27(439),
    dscp-value-0x28(440),
    dscp-value-0x29(441),
    dscp-value-0x2a(442),
    dscp-value-0x2b(443),
    dscp-value-0x2c(444),
    dscp-value-0x2d(445),
    dscp-value-0x2e(446),
    dscp-value-0x2f(447),
    dscp-value-0x30(448),
    dscp-value-0x31(449),
    dscp-value-0x32(450),
    dscp-value-0x33(451),
    dscp-value-0x34(452),
    dscp-value-0x35(453),
    dscp-value-0x36(454),
    dscp-value-0x37(455),
    dscp-value-0x38(456),
    dscp-value-0x39(457),
    dscp-value-0x3a(458),
    dscp-value-0x3b(459),
    dscp-value-0x3c(460),
    dscp-value-0x3d(461),
    dscp-value-0x3e(462),
    dscp-value-0x3f(463),
    unchanged(2000)
  }
  ACCESS read-write
  STATUS mandatory
  DESCRIPTION
    "Variable name: QOS_EGRESS_DIALIN_VPN_RULES.SET_TOSDSCP
    WebUi Label: New TOS/DSCP
    The rule's target for the DSCP/TOS field"
  ::= { mGuardQoSEgVPNDialinRuleEntry 8 }

-- QOS_EGRESS_DIALIN_VPN_RULES.FROM_IP
mGuardQoSEgVPNDialinRuSourceIP OBJECT-TYPE
  SYNTAX DisplayString
  ACCESS read-write
  STATUS mandatory
  DESCRIPTION
    "Variable name: QOS_EGRESS_DIALIN_VPN_RULES.FROM_IP
    WebUi Label: From IP
    The rule's source IP address"
  ::= { mGuardQoSEgVPNDialinRuleEntry 3 }

-- QOS_EGRESS_DIALIN_VPN_RULES.IN_IP
mGuardQoSEgVPNDialinRuDestIP OBJECT-TYPE
  SYNTAX DisplayString
  ACCESS read-write
  STATUS mandatory
  DESCRIPTION
    "Variable name: QOS_EGRESS_DIALIN_VPN_RULES.IN_IP
    WebUi Label: To IP
    The rule's destination IP address"
  ::= { mGuardQoSEgVPNDialinRuleEntry 5 }

-- QOS_EGRESS_DIALIN_VPN_RULES.QUEUE reference
mGuardQoSEgVPNDialinRuQRef OBJECT-TYPE
  SYNTAX OBJECT IDENTIFIER
  ACCESS read-write
  STATUS mandatory
  DESCRIPTION
    "Variable name: QOS_EGRESS_DIALIN_VPN_RULES.QUEUE
    WebUi Label: Queue name
    When this object contains the OID of an 'mGuardQoSEgVPNDialinQuIndex'
    object, the corresponding QoS Egress VPN dial-in queue is used as the
    rule's target queue."
  ::= { mGuardQoSEgVPNDialinRuleEntry 12 }

-- QOS_EGRESS_DIALIN_VPN_RULES.FIND_TOSDSCP
mGuardQoSEgVPNDialinRuFindDSCP OBJECT-TYPE
  SYNTAX INTEGER {
    tos-normal-service(100),
    tos-minimize-delay(101),
    tos-maximize-throughput(102),
    tos-maximize-reliability(103),
    tos-minimize-cost(104),
    dscp-class-be(200),
    dscp-class-ef(201),
    dscp-class-af11(202),
    dscp-class-af12(203),
    dscp-class-af13(204),
    dscp-class-af21(205),
    dscp-class-af22(206),
    dscp-class-af23(207),
    dscp-class-af31(208),
    dscp-class-af32(209),
    dscp-class-af33(210),
    dscp-class-af41(211),
    dscp-class-af42(212),
    dscp-class-af43(213),
    dscp-class-cs0(300),
    dscp-class-cs1(301),
    dscp-class-cs2(302),
    dscp-class-cs3(303),
    dscp-class-cs4(304),
    dscp-class-cs5(305),
    dscp-class-cs6(306),
    dscp-class-cs7(307),
    dscp-value-0x00(400),
    dscp-value-0x01(401),
    dscp-value-0x02(402),
    dscp-value-0x03(403),
    dscp-value-0x04(404),
    dscp-value-0x05(405),
    dscp-value-0x06(406),
    dscp-value-0x07(407),
    dscp-value-0x08(408),
    dscp-value-0x09(409),
    dscp-value-0x0a(410),
    dscp-value-0x0b(411),
    dscp-value-0x0c(412),
    dscp-value-0x0d(413),
    dscp-value-0x0e(414),
    dscp-value-0x0f(415),
    dscp-value-0x10(416),
    dscp-value-0x11(417),
    dscp-value-0x12(418),
    dscp-value-0x13(419),
    dscp-value-0x14(420),
    dscp-value-0x15(421),
    dscp-value-0x16(422),
    dscp-value-0x17(423),
    dscp-value-0x18(424),
    dscp-value-0x19(425),
    dscp-value-0x1a(426),
    dscp-value-0x1b(427),
    dscp-value-0x1c(428),
    dscp-value-0x1d(429),
    dscp-value-0x1e(430),
    dscp-value-0x1f(431),
    dscp-value-0x20(432),
    dscp-value-0x21(433),
    dscp-value-0x22(434),
    dscp-value-0x23(435),
    dscp-value-0x24(436),
    dscp-value-0x25(437),
    dscp-value-0x26(438),
    dscp-value-0x27(439),
    dscp-value-0x28(440),
    dscp-value-0x29(441),
    dscp-value-0x2a(442),
    dscp-value-0x2b(443),
    dscp-value-0x2c(444),
    dscp-value-0x2d(445),
    dscp-value-0x2e(446),
    dscp-value-0x2f(447),
    dscp-value-0x30(448),
    dscp-value-0x31(449),
    dscp-value-0x32(450),
    dscp-value-0x33(451),
    dscp-value-0x34(452),
    dscp-value-0x35(453),
    dscp-value-0x36(454),
    dscp-value-0x37(455),
    dscp-value-0x38(456),
    dscp-value-0x39(457),
    dscp-value-0x3a(458),
    dscp-value-0x3b(459),
    dscp-value-0x3c(460),
    dscp-value-0x3d(461),
    dscp-value-0x3e(462),
    dscp-value-0x3f(463),
    all(1000),
    tos-not-normal-service(1001),
    dscp-class-not-be(1002),
    dscp-class-not-cs0(1003),
    dscp-value-not-0(1004)
  }
  ACCESS read-write
  STATUS mandatory
  DESCRIPTION
    "Variable name: QOS_EGRESS_DIALIN_VPN_RULES.FIND_TOSDSCP
    WebUi Label: Current TOS/DSCP
    The rule's match on the DSCP/TOS field"
  ::= { mGuardQoSEgVPNDialinRuleEntry 7 }

-- QOS_EGRESS_DIALIN_VPN_RULES.IN_PORT
mGuardQoSEgVPNDialinRuDport OBJECT-TYPE
  SYNTAX DisplayString
  ACCESS read-write
  STATUS mandatory
  DESCRIPTION
    "Variable name: QOS_EGRESS_DIALIN_VPN_RULES.IN_PORT
    WebUi Label: To port
    The rule's destination port"
  ::= { mGuardQoSEgVPNDialinRuleEntry 6 }

-- QOS_EGRESS_DIALIN_VPN_UNIT
mGuardQoSEgVPNDialinUnit OBJECT-TYPE
  SYNTAX INTEGER {
    kbitpersec(1),
    packetpersec(2)
  }
  ACCESS read-write
  STATUS mandatory
  DESCRIPTION
    "Variable name: QOS_EGRESS_DIALIN_VPN_UNIT
    WebUi Label: Measurement unit
    Unit for egress QoS management."
  ::= { mGuardQoSEgVPNDialin 2 }

-- QOS_EGRESS_EXTERN2_DEFAULT reference
mGuardQoSEgExt2DefaultQueueRef OBJECT-TYPE
  SYNTAX OBJECT IDENTIFIER
  ACCESS read-write
  STATUS mandatory
  DESCRIPTION
    "Variable name: QOS_EGRESS_EXTERN2_DEFAULT
    WebUi Label: Default queue
    When this object contains the OID of an 'mGuardQoSEgExtern2QuIndex'
    object, the corresponding QoS Egress extern 2 queue is used as default
    queue."
  ::= { mGuardQoSEgExtern2 7 }

-- QOS_EGRESS_EXTERN2_ENABLE
mGuardQoSEgExtern2Enable OBJECT-TYPE
  SYNTAX INTEGER {
    yes(1),
    no(2)
  }
  ACCESS read-write
  STATUS mandatory
  DESCRIPTION
    "Variable name: QOS_EGRESS_EXTERN2_ENABLE
    WebUi Label: Enable Egress QoS
    Enable egress QoS queuing."
  ::= { mGuardQoSEgExtern2 1 }


-- QOS_EGRESS_EXTERN2_QUEUES table
mGuardQoSEgExtern2QueueTable OBJECT-TYPE
  SYNTAX SEQUENCE OF MGuardQoSEgExtern2QueueEntry
  ACCESS not-accessible
  STATUS mandatory
  DESCRIPTION
    "A table of QOS_EGRESS_EXTERN2_QUEUES"
  ::= { mGuardQoSEgExtern2 4 }

-- QOS_EGRESS_EXTERN2_QUEUES table entry
mGuardQoSEgExtern2QueueEntry OBJECT-TYPE
  SYNTAX MGuardQoSEgExtern2QueueEntry
  ACCESS not-accessible
  STATUS mandatory
  DESCRIPTION
    "An entry of QOS_EGRESS_EXTERN2_QUEUES"
  INDEX { mGuardQoSEgExtern2QuIndex }
  ::= { mGuardQoSEgExtern2QueueTable 1 }

MGuardQoSEgExtern2QueueEntry ::= SEQUENCE {
  mGuardQoSEgExtern2QuIndex                INTEGER,
  mGuardQoSEgExtern2QuName                 DisplayString,
  mGuardQoSEgExtern2QuMinRate              DisplayString,
  mGuardQoSEgExtern2QuMaxRate              DisplayString,
  mGuardQoSEgExtern2QuPref                 INTEGER,
  mGuardQoSEgExtern2QuComment              DisplayString,
  mGuardQoSEgExtern2QuRowStatus            RowStatus
}

-- QOS_EGRESS_EXTERN2_QUEUES table index
mGuardQoSEgExtern2QuIndex OBJECT-TYPE
  SYNTAX INTEGER (1..2147483647)
  ACCESS not-accessible
  STATUS mandatory
  DESCRIPTION
    "Index to QOS_EGRESS_EXTERN2_QUEUES"
  ::= { mGuardQoSEgExtern2QueueEntry 1 }

-- QOS_EGRESS_EXTERN2_QUEUES row status
mGuardQoSEgExtern2QuRowStatus OBJECT-TYPE
  SYNTAX RowStatus
  ACCESS read-write
  STATUS mandatory
  DESCRIPTION
    "RowStatus of QOS_EGRESS_EXTERN2_QUEUES"
  ::= { mGuardQoSEgExtern2QueueEntry 7 }

-- QOS_EGRESS_EXTERN2_QUEUES.COMMENT
mGuardQoSEgExtern2QuComment OBJECT-TYPE
  SYNTAX DisplayString
  ACCESS read-write
  STATUS mandatory
  DESCRIPTION
    "Variable name: QOS_EGRESS_EXTERN2_QUEUES.COMMENT
    WebUi Label: Comment
    Comment."
  ::= { mGuardQoSEgExtern2QueueEntry 6 }

-- QOS_EGRESS_EXTERN2_QUEUES.MIN_RATE
mGuardQoSEgExtern2QuMinRate OBJECT-TYPE
  SYNTAX DisplayString
  ACCESS read-write
  STATUS mandatory
  DESCRIPTION
    "Variable name: QOS_EGRESS_EXTERN2_QUEUES.MIN_RATE
    WebUi Label: Guaranteed
    Guaranteed rate: >=1 or 'unlimited'."
  ::= { mGuardQoSEgExtern2QueueEntry 3 }

-- QOS_EGRESS_EXTERN2_QUEUES.MAX_RATE
mGuardQoSEgExtern2QuMaxRate OBJECT-TYPE
  SYNTAX DisplayString
  ACCESS read-write
  STATUS mandatory
  DESCRIPTION
    "Variable name: QOS_EGRESS_EXTERN2_QUEUES.MAX_RATE
    WebUi Label: Upper limit
    Guaranteed rate: >=1 or 'unlimited'."
  ::= { mGuardQoSEgExtern2QueueEntry 4 }

-- QOS_EGRESS_EXTERN2_QUEUES.NAME
mGuardQoSEgExtern2QuName OBJECT-TYPE
  SYNTAX DisplayString
  ACCESS read-write
  STATUS mandatory
  DESCRIPTION
    "Variable name: QOS_EGRESS_EXTERN2_QUEUES.NAME
    WebUi Label: Name
    Name of the queue."
  ::= { mGuardQoSEgExtern2QueueEntry 2 }

-- QOS_EGRESS_EXTERN2_QUEUES.PREFERENCE
mGuardQoSEgExtern2QuPref OBJECT-TYPE
  SYNTAX INTEGER {
    low(1),
    medium(2),
    high(3)
  }
  ACCESS read-write
  STATUS mandatory
  DESCRIPTION
    "Variable name: QOS_EGRESS_EXTERN2_QUEUES.PREFERENCE
    WebUi Label: Priority
    Preference of queue."
  ::= { mGuardQoSEgExtern2QueueEntry 5 }

-- QOS_EGRESS_EXTERN2_RATE
mGuardQoSEgExtern2Rate OBJECT-TYPE
  SYNTAX DisplayString
  ACCESS read-write
  STATUS mandatory
  DESCRIPTION
    "Variable name: QOS_EGRESS_EXTERN2_RATE
    WebUi Label: Bandwidth
    Rate for egress QoS management: number >= 1 or 'unlimited'."
  ::= { mGuardQoSEgExtern2 3 }


-- QOS_EGRESS_EXTERN2_RULES table
mGuardQoSEgExtern2RuleTable OBJECT-TYPE
  SYNTAX SEQUENCE OF MGuardQoSEgExtern2RuleEntry
  ACCESS not-accessible
  STATUS mandatory
  DESCRIPTION
    "A table of QOS_EGRESS_EXTERN2_RULES"
  ::= { mGuardQoSEgExtern2 6 }

-- QOS_EGRESS_EXTERN2_RULES table entry
mGuardQoSEgExtern2RuleEntry OBJECT-TYPE
  SYNTAX MGuardQoSEgExtern2RuleEntry
  ACCESS not-accessible
  STATUS mandatory
  DESCRIPTION
    "An entry of QOS_EGRESS_EXTERN2_RULES"
  INDEX { mGuardQoSEgExtern2RuIndex }
  ::= { mGuardQoSEgExtern2RuleTable 1 }

MGuardQoSEgExtern2RuleEntry ::= SEQUENCE {
  mGuardQoSEgExtern2RuIndex                INTEGER,
  mGuardQoSEgExtern2RuProto                INTEGER,
  mGuardQoSEgExtern2RuSourceIP             DisplayString,
  mGuardQoSEgExtern2RuSport                DisplayString,
  mGuardQoSEgExtern2RuDestIP               DisplayString,
  mGuardQoSEgExtern2RuDport                DisplayString,
  mGuardQoSEgExtern2RuFindDSCP             INTEGER,
  mGuardQoSEgExtern2RuSetDSCP              INTEGER,
  mGuardQoSEgExtern2RuComment              DisplayString,
  mGuardQoSEgExtern2RuRowStatus            RowStatus,
  mGuardQoSEgExtern2RuQRef                 OBJECT IDENTIFIER
}

-- QOS_EGRESS_EXTERN2_RULES table index
mGuardQoSEgExtern2RuIndex OBJECT-TYPE
  SYNTAX INTEGER (1..2147483647)
  ACCESS not-accessible
  STATUS mandatory
  DESCRIPTION
    "Index to QOS_EGRESS_EXTERN2_RULES"
  ::= { mGuardQoSEgExtern2RuleEntry 1 }

-- QOS_EGRESS_EXTERN2_RULES row status
mGuardQoSEgExtern2RuRowStatus OBJECT-TYPE
  SYNTAX RowStatus
  ACCESS read-write
  STATUS mandatory
  DESCRIPTION
    "RowStatus of QOS_EGRESS_EXTERN2_RULES"
  ::= { mGuardQoSEgExtern2RuleEntry 11 }

-- QOS_EGRESS_EXTERN2_RULES.COMMENT
mGuardQoSEgExtern2RuComment OBJECT-TYPE
  SYNTAX DisplayString
  ACCESS read-write
  STATUS mandatory
  DESCRIPTION
    "Variable name: QOS_EGRESS_EXTERN2_RULES.COMMENT
    WebUi Label: Comment
    Comment."
  ::= { mGuardQoSEgExtern2RuleEntry 10 }

-- QOS_EGRESS_EXTERN2_RULES.FROM_PORT
mGuardQoSEgExtern2RuSport OBJECT-TYPE
  SYNTAX DisplayString
  ACCESS read-write
  STATUS mandatory
  DESCRIPTION
    "Variable name: QOS_EGRESS_EXTERN2_RULES.FROM_PORT
    WebUi Label: From port
    The rule's source port"
  ::= { mGuardQoSEgExtern2RuleEntry 4 }

-- QOS_EGRESS_EXTERN2_RULES.PROTO
mGuardQoSEgExtern2RuProto OBJECT-TYPE
  SYNTAX INTEGER {
    icmp(1),
    tcp(6),
    udp(17),
    esp(50),
    all(256)
  }
  ACCESS read-write
  STATUS mandatory
  DESCRIPTION
    "Variable name: QOS_EGRESS_EXTERN2_RULES.PROTO
    WebUi Label: Protocol
    The rule's protocol"
  ::= { mGuardQoSEgExtern2RuleEntry 2 }

-- QOS_EGRESS_EXTERN2_RULES.SET_TOSDSCP
mGuardQoSEgExtern2RuSetDSCP OBJECT-TYPE
  SYNTAX INTEGER {
    tos-normal-service(100),
    tos-minimize-delay(101),
    tos-maximize-throughput(102),
    tos-maximize-reliability(103),
    tos-minimize-cost(104),
    dscp-class-be(200),
    dscp-class-ef(201),
    dscp-class-af11(202),
    dscp-class-af12(203),
    dscp-class-af13(204),
    dscp-class-af21(205),
    dscp-class-af22(206),
    dscp-class-af23(207),
    dscp-class-af31(208),
    dscp-class-af32(209),
    dscp-class-af33(210),
    dscp-class-af41(211),
    dscp-class-af42(212),
    dscp-class-af43(213),
    dscp-class-cs0(300),
    dscp-class-cs1(301),
    dscp-class-cs2(302),
    dscp-class-cs3(303),
    dscp-class-cs4(304),
    dscp-class-cs5(305),
    dscp-class-cs6(306),
    dscp-class-cs7(307),
    dscp-value-0x00(400),
    dscp-value-0x01(401),
    dscp-value-0x02(402),
    dscp-value-0x03(403),
    dscp-value-0x04(404),
    dscp-value-0x05(405),
    dscp-value-0x06(406),
    dscp-value-0x07(407),
    dscp-value-0x08(408),
    dscp-value-0x09(409),
    dscp-value-0x0a(410),
    dscp-value-0x0b(411),
    dscp-value-0x0c(412),
    dscp-value-0x0d(413),
    dscp-value-0x0e(414),
    dscp-value-0x0f(415),
    dscp-value-0x10(416),
    dscp-value-0x11(417),
    dscp-value-0x12(418),
    dscp-value-0x13(419),
    dscp-value-0x14(420),
    dscp-value-0x15(421),
    dscp-value-0x16(422),
    dscp-value-0x17(423),
    dscp-value-0x18(424),
    dscp-value-0x19(425),
    dscp-value-0x1a(426),
    dscp-value-0x1b(427),
    dscp-value-0x1c(428),
    dscp-value-0x1d(429),
    dscp-value-0x1e(430),
    dscp-value-0x1f(431),
    dscp-value-0x20(432),
    dscp-value-0x21(433),
    dscp-value-0x22(434),
    dscp-value-0x23(435),
    dscp-value-0x24(436),
    dscp-value-0x25(437),
    dscp-value-0x26(438),
    dscp-value-0x27(439),
    dscp-value-0x28(440),
    dscp-value-0x29(441),
    dscp-value-0x2a(442),
    dscp-value-0x2b(443),
    dscp-value-0x2c(444),
    dscp-value-0x2d(445),
    dscp-value-0x2e(446),
    dscp-value-0x2f(447),
    dscp-value-0x30(448),
    dscp-value-0x31(449),
    dscp-value-0x32(450),
    dscp-value-0x33(451),
    dscp-value-0x34(452),
    dscp-value-0x35(453),
    dscp-value-0x36(454),
    dscp-value-0x37(455),
    dscp-value-0x38(456),
    dscp-value-0x39(457),
    dscp-value-0x3a(458),
    dscp-value-0x3b(459),
    dscp-value-0x3c(460),
    dscp-value-0x3d(461),
    dscp-value-0x3e(462),
    dscp-value-0x3f(463),
    unchanged(2000)
  }
  ACCESS read-write
  STATUS mandatory
  DESCRIPTION
    "Variable name: QOS_EGRESS_EXTERN2_RULES.SET_TOSDSCP
    WebUi Label: New TOS/DSCP
    The rule's target for the DSCP/TOS field"
  ::= { mGuardQoSEgExtern2RuleEntry 8 }

-- QOS_EGRESS_EXTERN2_RULES.FROM_IP
mGuardQoSEgExtern2RuSourceIP OBJECT-TYPE
  SYNTAX DisplayString
  ACCESS read-write
  STATUS mandatory
  DESCRIPTION
    "Variable name: QOS_EGRESS_EXTERN2_RULES.FROM_IP
    WebUi Label: From IP
    The rule's source IP address"
  ::= { mGuardQoSEgExtern2RuleEntry 3 }

-- QOS_EGRESS_EXTERN2_RULES.IN_IP
mGuardQoSEgExtern2RuDestIP OBJECT-TYPE
  SYNTAX DisplayString
  ACCESS read-write
  STATUS mandatory
  DESCRIPTION
    "Variable name: QOS_EGRESS_EXTERN2_RULES.IN_IP
    WebUi Label: To IP
    The rule's destination IP address"
  ::= { mGuardQoSEgExtern2RuleEntry 5 }

-- QOS_EGRESS_EXTERN2_RULES.QUEUE reference
mGuardQoSEgExtern2RuQRef OBJECT-TYPE
  SYNTAX OBJECT IDENTIFIER
  ACCESS read-write
  STATUS mandatory
  DESCRIPTION
    "Variable name: QOS_EGRESS_EXTERN2_RULES.QUEUE
    WebUi Label: Queue name
    When this object contains the OID of an 'mGuardQoSEgExtern2QuIndex'
    object, the corresponding QoS Egress extern 2 queue is used as the
    rule's target queue."
  ::= { mGuardQoSEgExtern2RuleEntry 12 }

-- QOS_EGRESS_EXTERN2_RULES.FIND_TOSDSCP
mGuardQoSEgExtern2RuFindDSCP OBJECT-TYPE
  SYNTAX INTEGER {
    tos-normal-service(100),
    tos-minimize-delay(101),
    tos-maximize-throughput(102),
    tos-maximize-reliability(103),
    tos-minimize-cost(104),
    dscp-class-be(200),
    dscp-class-ef(201),
    dscp-class-af11(202),
    dscp-class-af12(203),
    dscp-class-af13(204),
    dscp-class-af21(205),
    dscp-class-af22(206),
    dscp-class-af23(207),
    dscp-class-af31(208),
    dscp-class-af32(209),
    dscp-class-af33(210),
    dscp-class-af41(211),
    dscp-class-af42(212),
    dscp-class-af43(213),
    dscp-class-cs0(300),
    dscp-class-cs1(301),
    dscp-class-cs2(302),
    dscp-class-cs3(303),
    dscp-class-cs4(304),
    dscp-class-cs5(305),
    dscp-class-cs6(306),
    dscp-class-cs7(307),
    dscp-value-0x00(400),
    dscp-value-0x01(401),
    dscp-value-0x02(402),
    dscp-value-0x03(403),
    dscp-value-0x04(404),
    dscp-value-0x05(405),
    dscp-value-0x06(406),
    dscp-value-0x07(407),
    dscp-value-0x08(408),
    dscp-value-0x09(409),
    dscp-value-0x0a(410),
    dscp-value-0x0b(411),
    dscp-value-0x0c(412),
    dscp-value-0x0d(413),
    dscp-value-0x0e(414),
    dscp-value-0x0f(415),
    dscp-value-0x10(416),
    dscp-value-0x11(417),
    dscp-value-0x12(418),
    dscp-value-0x13(419),
    dscp-value-0x14(420),
    dscp-value-0x15(421),
    dscp-value-0x16(422),
    dscp-value-0x17(423),
    dscp-value-0x18(424),
    dscp-value-0x19(425),
    dscp-value-0x1a(426),
    dscp-value-0x1b(427),
    dscp-value-0x1c(428),
    dscp-value-0x1d(429),
    dscp-value-0x1e(430),
    dscp-value-0x1f(431),
    dscp-value-0x20(432),
    dscp-value-0x21(433),
    dscp-value-0x22(434),
    dscp-value-0x23(435),
    dscp-value-0x24(436),
    dscp-value-0x25(437),
    dscp-value-0x26(438),
    dscp-value-0x27(439),
    dscp-value-0x28(440),
    dscp-value-0x29(441),
    dscp-value-0x2a(442),
    dscp-value-0x2b(443),
    dscp-value-0x2c(444),
    dscp-value-0x2d(445),
    dscp-value-0x2e(446),
    dscp-value-0x2f(447),
    dscp-value-0x30(448),
    dscp-value-0x31(449),
    dscp-value-0x32(450),
    dscp-value-0x33(451),
    dscp-value-0x34(452),
    dscp-value-0x35(453),
    dscp-value-0x36(454),
    dscp-value-0x37(455),
    dscp-value-0x38(456),
    dscp-value-0x39(457),
    dscp-value-0x3a(458),
    dscp-value-0x3b(459),
    dscp-value-0x3c(460),
    dscp-value-0x3d(461),
    dscp-value-0x3e(462),
    dscp-value-0x3f(463),
    all(1000),
    tos-not-normal-service(1001),
    dscp-class-not-be(1002),
    dscp-class-not-cs0(1003),
    dscp-value-not-0(1004)
  }
  ACCESS read-write
  STATUS mandatory
  DESCRIPTION
    "Variable name: QOS_EGRESS_EXTERN2_RULES.FIND_TOSDSCP
    WebUi Label: Current TOS/DSCP
    The rule's match on the DSCP/TOS field"
  ::= { mGuardQoSEgExtern2RuleEntry 7 }

-- QOS_EGRESS_EXTERN2_RULES.IN_PORT
mGuardQoSEgExtern2RuDport OBJECT-TYPE
  SYNTAX DisplayString
  ACCESS read-write
  STATUS mandatory
  DESCRIPTION
    "Variable name: QOS_EGRESS_EXTERN2_RULES.IN_PORT
    WebUi Label: To port
    The rule's destination port"
  ::= { mGuardQoSEgExtern2RuleEntry 6 }

-- QOS_EGRESS_EXTERN2_UNIT
mGuardQoSEgExtern2Unit OBJECT-TYPE
  SYNTAX INTEGER {
    kbitpersec(1),
    packetpersec(2)
  }
  ACCESS read-write
  STATUS mandatory
  DESCRIPTION
    "Variable name: QOS_EGRESS_EXTERN2_UNIT
    WebUi Label: Measurement unit
    Unit for egress QoS management."
  ::= { mGuardQoSEgExtern2 2 }

-- QOS_EGRESS_EXTERN2_VPN_DEFAULT reference
mGuardQoSEgVPNExt2DefaultQRef OBJECT-TYPE
  SYNTAX OBJECT IDENTIFIER
  ACCESS read-write
  STATUS mandatory
  DESCRIPTION
    "Variable name: QOS_EGRESS_EXTERN2_VPN_DEFAULT
    WebUi Label: Default queue
    When this object contains the OID of an 'mGuardQoSEgVPNExtern2QuIndex'
    object, the corresponding QoS Egress VPN extern 2 queue is used as
    default queue."
  ::= { mGuardQoSEgVPNExtern2 7 }

-- QOS_EGRESS_EXTERN2_VPN_ENABLE
mGuardQoSEgVPNExtern2Enable OBJECT-TYPE
  SYNTAX INTEGER {
    yes(1),
    no(2)
  }
  ACCESS read-write
  STATUS mandatory
  DESCRIPTION
    "Variable name: QOS_EGRESS_EXTERN2_VPN_ENABLE
    WebUi Label: Enable Egress QoS
    Enable egress QoS queuing."
  ::= { mGuardQoSEgVPNExtern2 1 }


-- QOS_EGRESS_EXTERN2_VPN_QUEUES table
mGuardQoSEgVPNExtern2QueueTable OBJECT-TYPE
  SYNTAX SEQUENCE OF MGuardQoSEgVPNExtern2QueueEntry
  ACCESS not-accessible
  STATUS mandatory
  DESCRIPTION
    "A table of QOS_EGRESS_EXTERN2_VPN_QUEUES"
  ::= { mGuardQoSEgVPNExtern2 4 }

-- QOS_EGRESS_EXTERN2_VPN_QUEUES table entry
mGuardQoSEgVPNExtern2QueueEntry OBJECT-TYPE
  SYNTAX MGuardQoSEgVPNExtern2QueueEntry
  ACCESS not-accessible
  STATUS mandatory
  DESCRIPTION
    "An entry of QOS_EGRESS_EXTERN2_VPN_QUEUES"
  INDEX { mGuardQoSEgVPNExtern2QuIndex }
  ::= { mGuardQoSEgVPNExtern2QueueTable 1 }

MGuardQoSEgVPNExtern2QueueEntry ::= SEQUENCE {
  mGuardQoSEgVPNExtern2QuIndex             INTEGER,
  mGuardQoSEgVPNExtern2QuName              DisplayString,
  mGuardQoSEgVPNExtern2QuMinRate           DisplayString,
  mGuardQoSEgVPNExtern2QuMaxRate           DisplayString,
  mGuardQoSEgVPNExtern2QuPref              INTEGER,
  mGuardQoSEgVPNExtern2QuComment           DisplayString,
  mGuardQoSEgVPNExtern2QuRowStatus         RowStatus
}

-- QOS_EGRESS_EXTERN2_VPN_QUEUES table index
mGuardQoSEgVPNExtern2QuIndex OBJECT-TYPE
  SYNTAX INTEGER (1..2147483647)
  ACCESS not-accessible
  STATUS mandatory
  DESCRIPTION
    "Index to QOS_EGRESS_EXTERN2_VPN_QUEUES"
  ::= { mGuardQoSEgVPNExtern2QueueEntry 1 }

-- QOS_EGRESS_EXTERN2_VPN_QUEUES row status
mGuardQoSEgVPNExtern2QuRowStatus OBJECT-TYPE
  SYNTAX RowStatus
  ACCESS read-write
  STATUS mandatory
  DESCRIPTION
    "RowStatus of QOS_EGRESS_EXTERN2_VPN_QUEUES"
  ::= { mGuardQoSEgVPNExtern2QueueEntry 7 }

-- QOS_EGRESS_EXTERN2_VPN_QUEUES.COMMENT
mGuardQoSEgVPNExtern2QuComment OBJECT-TYPE
  SYNTAX DisplayString
  ACCESS read-write
  STATUS mandatory
  DESCRIPTION
    "Variable name: QOS_EGRESS_EXTERN2_VPN_QUEUES.COMMENT
    WebUi Label: Comment
    Comment."
  ::= { mGuardQoSEgVPNExtern2QueueEntry 6 }

-- QOS_EGRESS_EXTERN2_VPN_QUEUES.MIN_RATE
mGuardQoSEgVPNExtern2QuMinRate OBJECT-TYPE
  SYNTAX DisplayString
  ACCESS read-write
  STATUS mandatory
  DESCRIPTION
    "Variable name: QOS_EGRESS_EXTERN2_VPN_QUEUES.MIN_RATE
    WebUi Label: Guaranteed
    Guaranteed rate: >=1 or 'unlimited'."
  ::= { mGuardQoSEgVPNExtern2QueueEntry 3 }

-- QOS_EGRESS_EXTERN2_VPN_QUEUES.MAX_RATE
mGuardQoSEgVPNExtern2QuMaxRate OBJECT-TYPE
  SYNTAX DisplayString
  ACCESS read-write
  STATUS mandatory
  DESCRIPTION
    "Variable name: QOS_EGRESS_EXTERN2_VPN_QUEUES.MAX_RATE
    WebUi Label: Upper limit
    Guaranteed rate: >=1 or 'unlimited'."
  ::= { mGuardQoSEgVPNExtern2QueueEntry 4 }

-- QOS_EGRESS_EXTERN2_VPN_QUEUES.NAME
mGuardQoSEgVPNExtern2QuName OBJECT-TYPE
  SYNTAX DisplayString
  ACCESS read-write
  STATUS mandatory
  DESCRIPTION
    "Variable name: QOS_EGRESS_EXTERN2_VPN_QUEUES.NAME
    WebUi Label: Name
    Name of the queue."
  ::= { mGuardQoSEgVPNExtern2QueueEntry 2 }

-- QOS_EGRESS_EXTERN2_VPN_QUEUES.PREFERENCE
mGuardQoSEgVPNExtern2QuPref OBJECT-TYPE
  SYNTAX INTEGER {
    low(1),
    medium(2),
    high(3)
  }
  ACCESS read-write
  STATUS mandatory
  DESCRIPTION
    "Variable name: QOS_EGRESS_EXTERN2_VPN_QUEUES.PREFERENCE
    WebUi Label: Priority
    Preference of queue."
  ::= { mGuardQoSEgVPNExtern2QueueEntry 5 }

-- QOS_EGRESS_EXTERN2_VPN_RATE
mGuardQoSEgVPNExtern2Rate OBJECT-TYPE
  SYNTAX DisplayString
  ACCESS read-write
  STATUS mandatory
  DESCRIPTION
    "Variable name: QOS_EGRESS_EXTERN2_VPN_RATE
    WebUi Label: Bandwidth
    Rate for egress QoS management: number >= 1 or 'unlimited'."
  ::= { mGuardQoSEgVPNExtern2 3 }


-- QOS_EGRESS_EXTERN2_VPN_RULES table
mGuardQoSEgVPNExtern2RuleTable OBJECT-TYPE
  SYNTAX SEQUENCE OF MGuardQoSEgVPNExtern2RuleEntry
  ACCESS not-accessible
  STATUS mandatory
  DESCRIPTION
    "A table of QOS_EGRESS_EXTERN2_VPN_RULES"
  ::= { mGuardQoSEgVPNExtern2 6 }

-- QOS_EGRESS_EXTERN2_VPN_RULES table entry
mGuardQoSEgVPNExtern2RuleEntry OBJECT-TYPE
  SYNTAX MGuardQoSEgVPNExtern2RuleEntry
  ACCESS not-accessible
  STATUS mandatory
  DESCRIPTION
    "An entry of QOS_EGRESS_EXTERN2_VPN_RULES"
  INDEX { mGuardQoSEgVPNExtern2RuIndex }
  ::= { mGuardQoSEgVPNExtern2RuleTable 1 }

MGuardQoSEgVPNExtern2RuleEntry ::= SEQUENCE {
  mGuardQoSEgVPNExtern2RuIndex             INTEGER,
  mGuardQoSEgVPNExtern2RuProto             INTEGER,
  mGuardQoSEgVPNExtern2RuSourceIP          DisplayString,
  mGuardQoSEgVPNExtern2RuSport             DisplayString,
  mGuardQoSEgVPNExtern2RuDestIP            DisplayString,
  mGuardQoSEgVPNExtern2RuDport             DisplayString,
  mGuardQoSEgVPNExtern2RuFindDSCP          INTEGER,
  mGuardQoSEgVPNExtern2RuSetDSCP           INTEGER,
  mGuardQoSEgVPNExtern2RuComment           DisplayString,
  mGuardQoSEgVPNExtern2RuRowStatus         RowStatus,
  mGuardQoSEgVPNExtern2RuQRef              OBJECT IDENTIFIER
}

-- QOS_EGRESS_EXTERN2_VPN_RULES table index
mGuardQoSEgVPNExtern2RuIndex OBJECT-TYPE
  SYNTAX INTEGER (1..2147483647)
  ACCESS not-accessible
  STATUS mandatory
  DESCRIPTION
    "Index to QOS_EGRESS_EXTERN2_VPN_RULES"
  ::= { mGuardQoSEgVPNExtern2RuleEntry 1 }

-- QOS_EGRESS_EXTERN2_VPN_RULES row status
mGuardQoSEgVPNExtern2RuRowStatus OBJECT-TYPE
  SYNTAX RowStatus
  ACCESS read-write
  STATUS mandatory
  DESCRIPTION
    "RowStatus of QOS_EGRESS_EXTERN2_VPN_RULES"
  ::= { mGuardQoSEgVPNExtern2RuleEntry 11 }

-- QOS_EGRESS_EXTERN2_VPN_RULES.COMMENT
mGuardQoSEgVPNExtern2RuComment OBJECT-TYPE
  SYNTAX DisplayString
  ACCESS read-write
  STATUS mandatory
  DESCRIPTION
    "Variable name: QOS_EGRESS_EXTERN2_VPN_RULES.COMMENT
    WebUi Label: Comment
    Comment."
  ::= { mGuardQoSEgVPNExtern2RuleEntry 10 }

-- QOS_EGRESS_EXTERN2_VPN_RULES.FROM_PORT
mGuardQoSEgVPNExtern2RuSport OBJECT-TYPE
  SYNTAX DisplayString
  ACCESS read-write
  STATUS mandatory
  DESCRIPTION
    "Variable name: QOS_EGRESS_EXTERN2_VPN_RULES.FROM_PORT
    WebUi Label: From port
    The rule's source port"
  ::= { mGuardQoSEgVPNExtern2RuleEntry 4 }

-- QOS_EGRESS_EXTERN2_VPN_RULES.PROTO
mGuardQoSEgVPNExtern2RuProto OBJECT-TYPE
  SYNTAX INTEGER {
    icmp(1),
    tcp(6),
    udp(17),
    esp(50),
    all(256)
  }
  ACCESS read-write
  STATUS mandatory
  DESCRIPTION
    "Variable name: QOS_EGRESS_EXTERN2_VPN_RULES.PROTO
    WebUi Label: Protocol
    The rule's protocol"
  ::= { mGuardQoSEgVPNExtern2RuleEntry 2 }

-- QOS_EGRESS_EXTERN2_VPN_RULES.SET_TOSDSCP
mGuardQoSEgVPNExtern2RuSetDSCP OBJECT-TYPE
  SYNTAX INTEGER {
    tos-normal-service(100),
    tos-minimize-delay(101),
    tos-maximize-throughput(102),
    tos-maximize-reliability(103),
    tos-minimize-cost(104),
    dscp-class-be(200),
    dscp-class-ef(201),
    dscp-class-af11(202),
    dscp-class-af12(203),
    dscp-class-af13(204),
    dscp-class-af21(205),
    dscp-class-af22(206),
    dscp-class-af23(207),
    dscp-class-af31(208),
    dscp-class-af32(209),
    dscp-class-af33(210),
    dscp-class-af41(211),
    dscp-class-af42(212),
    dscp-class-af43(213),
    dscp-class-cs0(300),
    dscp-class-cs1(301),
    dscp-class-cs2(302),
    dscp-class-cs3(303),
    dscp-class-cs4(304),
    dscp-class-cs5(305),
    dscp-class-cs6(306),
    dscp-class-cs7(307),
    dscp-value-0x00(400),
    dscp-value-0x01(401),
    dscp-value-0x02(402),
    dscp-value-0x03(403),
    dscp-value-0x04(404),
    dscp-value-0x05(405),
    dscp-value-0x06(406),
    dscp-value-0x07(407),
    dscp-value-0x08(408),
    dscp-value-0x09(409),
    dscp-value-0x0a(410),
    dscp-value-0x0b(411),
    dscp-value-0x0c(412),
    dscp-value-0x0d(413),
    dscp-value-0x0e(414),
    dscp-value-0x0f(415),
    dscp-value-0x10(416),
    dscp-value-0x11(417),
    dscp-value-0x12(418),
    dscp-value-0x13(419),
    dscp-value-0x14(420),
    dscp-value-0x15(421),
    dscp-value-0x16(422),
    dscp-value-0x17(423),
    dscp-value-0x18(424),
    dscp-value-0x19(425),
    dscp-value-0x1a(426),
    dscp-value-0x1b(427),
    dscp-value-0x1c(428),
    dscp-value-0x1d(429),
    dscp-value-0x1e(430),
    dscp-value-0x1f(431),
    dscp-value-0x20(432),
    dscp-value-0x21(433),
    dscp-value-0x22(434),
    dscp-value-0x23(435),
    dscp-value-0x24(436),
    dscp-value-0x25(437),
    dscp-value-0x26(438),
    dscp-value-0x27(439),
    dscp-value-0x28(440),
    dscp-value-0x29(441),
    dscp-value-0x2a(442),
    dscp-value-0x2b(443),
    dscp-value-0x2c(444),
    dscp-value-0x2d(445),
    dscp-value-0x2e(446),
    dscp-value-0x2f(447),
    dscp-value-0x30(448),
    dscp-value-0x31(449),
    dscp-value-0x32(450),
    dscp-value-0x33(451),
    dscp-value-0x34(452),
    dscp-value-0x35(453),
    dscp-value-0x36(454),
    dscp-value-0x37(455),
    dscp-value-0x38(456),
    dscp-value-0x39(457),
    dscp-value-0x3a(458),
    dscp-value-0x3b(459),
    dscp-value-0x3c(460),
    dscp-value-0x3d(461),
    dscp-value-0x3e(462),
    dscp-value-0x3f(463),
    unchanged(2000)
  }
  ACCESS read-write
  STATUS mandatory
  DESCRIPTION
    "Variable name: QOS_EGRESS_EXTERN2_VPN_RULES.SET_TOSDSCP
    WebUi Label: New TOS/DSCP
    The rule's target for the DSCP/TOS field"
  ::= { mGuardQoSEgVPNExtern2RuleEntry 8 }

-- QOS_EGRESS_EXTERN2_VPN_RULES.FROM_IP
mGuardQoSEgVPNExtern2RuSourceIP OBJECT-TYPE
  SYNTAX DisplayString
  ACCESS read-write
  STATUS mandatory
  DESCRIPTION
    "Variable name: QOS_EGRESS_EXTERN2_VPN_RULES.FROM_IP
    WebUi Label: From IP
    The rule's source IP address"
  ::= { mGuardQoSEgVPNExtern2RuleEntry 3 }

-- QOS_EGRESS_EXTERN2_VPN_RULES.IN_IP
mGuardQoSEgVPNExtern2RuDestIP OBJECT-TYPE
  SYNTAX DisplayString
  ACCESS read-write
  STATUS mandatory
  DESCRIPTION
    "Variable name: QOS_EGRESS_EXTERN2_VPN_RULES.IN_IP
    WebUi Label: To IP
    The rule's destination IP address"
  ::= { mGuardQoSEgVPNExtern2RuleEntry 5 }

-- QOS_EGRESS_EXTERN2_VPN_RULES.QUEUE reference
mGuardQoSEgVPNExtern2RuQRef OBJECT-TYPE
  SYNTAX OBJECT IDENTIFIER
  ACCESS read-write
  STATUS mandatory
  DESCRIPTION
    "Variable name: QOS_EGRESS_EXTERN2_VPN_RULES.QUEUE
    WebUi Label: Queue name
    When this object contains the OID of an 'mGuardQoSEgVPNExtern2QuIndex'
    object, the corresponding QoS Egress VPN extern 2 queue is used as the
    rule's target queue."
  ::= { mGuardQoSEgVPNExtern2RuleEntry 12 }

-- QOS_EGRESS_EXTERN2_VPN_RULES.FIND_TOSDSCP
mGuardQoSEgVPNExtern2RuFindDSCP OBJECT-TYPE
  SYNTAX INTEGER {
    tos-normal-service(100),
    tos-minimize-delay(101),
    tos-maximize-throughput(102),
    tos-maximize-reliability(103),
    tos-minimize-cost(104),
    dscp-class-be(200),
    dscp-class-ef(201),
    dscp-class-af11(202),
    dscp-class-af12(203),
    dscp-class-af13(204),
    dscp-class-af21(205),
    dscp-class-af22(206),
    dscp-class-af23(207),
    dscp-class-af31(208),
    dscp-class-af32(209),
    dscp-class-af33(210),
    dscp-class-af41(211),
    dscp-class-af42(212),
    dscp-class-af43(213),
    dscp-class-cs0(300),
    dscp-class-cs1(301),
    dscp-class-cs2(302),
    dscp-class-cs3(303),
    dscp-class-cs4(304),
    dscp-class-cs5(305),
    dscp-class-cs6(306),
    dscp-class-cs7(307),
    dscp-value-0x00(400),
    dscp-value-0x01(401),
    dscp-value-0x02(402),
    dscp-value-0x03(403),
    dscp-value-0x04(404),
    dscp-value-0x05(405),
    dscp-value-0x06(406),
    dscp-value-0x07(407),
    dscp-value-0x08(408),
    dscp-value-0x09(409),
    dscp-value-0x0a(410),
    dscp-value-0x0b(411),
    dscp-value-0x0c(412),
    dscp-value-0x0d(413),
    dscp-value-0x0e(414),
    dscp-value-0x0f(415),
    dscp-value-0x10(416),
    dscp-value-0x11(417),
    dscp-value-0x12(418),
    dscp-value-0x13(419),
    dscp-value-0x14(420),
    dscp-value-0x15(421),
    dscp-value-0x16(422),
    dscp-value-0x17(423),
    dscp-value-0x18(424),
    dscp-value-0x19(425),
    dscp-value-0x1a(426),
    dscp-value-0x1b(427),
    dscp-value-0x1c(428),
    dscp-value-0x1d(429),
    dscp-value-0x1e(430),
    dscp-value-0x1f(431),
    dscp-value-0x20(432),
    dscp-value-0x21(433),
    dscp-value-0x22(434),
    dscp-value-0x23(435),
    dscp-value-0x24(436),
    dscp-value-0x25(437),
    dscp-value-0x26(438),
    dscp-value-0x27(439),
    dscp-value-0x28(440),
    dscp-value-0x29(441),
    dscp-value-0x2a(442),
    dscp-value-0x2b(443),
    dscp-value-0x2c(444),
    dscp-value-0x2d(445),
    dscp-value-0x2e(446),
    dscp-value-0x2f(447),
    dscp-value-0x30(448),
    dscp-value-0x31(449),
    dscp-value-0x32(450),
    dscp-value-0x33(451),
    dscp-value-0x34(452),
    dscp-value-0x35(453),
    dscp-value-0x36(454),
    dscp-value-0x37(455),
    dscp-value-0x38(456),
    dscp-value-0x39(457),
    dscp-value-0x3a(458),
    dscp-value-0x3b(459),
    dscp-value-0x3c(460),
    dscp-value-0x3d(461),
    dscp-value-0x3e(462),
    dscp-value-0x3f(463),
    all(1000),
    tos-not-normal-service(1001),
    dscp-class-not-be(1002),
    dscp-class-not-cs0(1003),
    dscp-value-not-0(1004)
  }
  ACCESS read-write
  STATUS mandatory
  DESCRIPTION
    "Variable name: QOS_EGRESS_EXTERN2_VPN_RULES.FIND_TOSDSCP
    WebUi Label: Current TOS/DSCP
    The rule's match on the DSCP/TOS field"
  ::= { mGuardQoSEgVPNExtern2RuleEntry 7 }

-- QOS_EGRESS_EXTERN2_VPN_RULES.IN_PORT
mGuardQoSEgVPNExtern2RuDport OBJECT-TYPE
  SYNTAX DisplayString
  ACCESS read-write
  STATUS mandatory
  DESCRIPTION
    "Variable name: QOS_EGRESS_EXTERN2_VPN_RULES.IN_PORT
    WebUi Label: To port
    The rule's destination port"
  ::= { mGuardQoSEgVPNExtern2RuleEntry 6 }

-- QOS_EGRESS_EXTERN2_VPN_UNIT
mGuardQoSEgVPNExtern2Unit OBJECT-TYPE
  SYNTAX INTEGER {
    kbitpersec(1),
    packetpersec(2)
  }
  ACCESS read-write
  STATUS mandatory
  DESCRIPTION
    "Variable name: QOS_EGRESS_EXTERN2_VPN_UNIT
    WebUi Label: Measurement unit
    Unit for egress QoS management."
  ::= { mGuardQoSEgVPNExtern2 2 }

-- QOS_EGRESS_EXTERN_DEFAULT reference
mGuardQoSEgExtDefaultQueueRef OBJECT-TYPE
  SYNTAX OBJECT IDENTIFIER
  ACCESS read-write
  STATUS mandatory
  DESCRIPTION
    "Variable name: QOS_EGRESS_EXTERN_DEFAULT
    WebUi Label: Default queue
    When this object contains the OID of an 'mGuardQoSEgExtQuIndex'
    object, the corresponding QoS Egress extern queue is used as default
    queue."
  ::= { mGuardQoSEgExtern 7 }

-- QOS_EGRESS_EXTERN_ENABLE
mGuardQoSEgExternEnable OBJECT-TYPE
  SYNTAX INTEGER {
    yes(1),
    no(2)
  }
  ACCESS read-write
  STATUS mandatory
  DESCRIPTION
    "Variable name: QOS_EGRESS_EXTERN_ENABLE
    WebUi Label: Enable Egress QoS
    Enable egress QoS queuing."
  ::= { mGuardQoSEgExtern 1 }


-- QOS_EGRESS_EXTERN_QUEUES table
mGuardQoSEgExternQueueTable OBJECT-TYPE
  SYNTAX SEQUENCE OF MGuardQoSEgExternQueueEntry
  ACCESS not-accessible
  STATUS mandatory
  DESCRIPTION
    "A table of QOS_EGRESS_EXTERN_QUEUES"
  ::= { mGuardQoSEgExtern 4 }

-- QOS_EGRESS_EXTERN_QUEUES table entry
mGuardQoSEgExternQueueEntry OBJECT-TYPE
  SYNTAX MGuardQoSEgExternQueueEntry
  ACCESS not-accessible
  STATUS mandatory
  DESCRIPTION
    "An entry of QOS_EGRESS_EXTERN_QUEUES"
  INDEX { mGuardQoSEgExtQuIndex }
  ::= { mGuardQoSEgExternQueueTable 1 }

MGuardQoSEgExternQueueEntry ::= SEQUENCE {
  mGuardQoSEgExtQuIndex                    INTEGER,
  mGuardQoSEgExtQuName                     DisplayString,
  mGuardQoSEgExtQuMinRate                  DisplayString,
  mGuardQoSEgExtQuMaxRate                  DisplayString,
  mGuardQoSEgExtQuPref                     INTEGER,
  mGuardQoSEgExtQuComment                  DisplayString,
  mGuardQoSEgExtQuRowStatus                RowStatus
}

-- QOS_EGRESS_EXTERN_QUEUES table index
mGuardQoSEgExtQuIndex OBJECT-TYPE
  SYNTAX INTEGER (1..2147483647)
  ACCESS not-accessible
  STATUS mandatory
  DESCRIPTION
    "Index to QOS_EGRESS_EXTERN_QUEUES"
  ::= { mGuardQoSEgExternQueueEntry 1 }

-- QOS_EGRESS_EXTERN_QUEUES row status
mGuardQoSEgExtQuRowStatus OBJECT-TYPE
  SYNTAX RowStatus
  ACCESS read-write
  STATUS mandatory
  DESCRIPTION
    "RowStatus of QOS_EGRESS_EXTERN_QUEUES"
  ::= { mGuardQoSEgExternQueueEntry 7 }

-- QOS_EGRESS_EXTERN_QUEUES.COMMENT
mGuardQoSEgExtQuComment OBJECT-TYPE
  SYNTAX DisplayString
  ACCESS read-write
  STATUS mandatory
  DESCRIPTION
    "Variable name: QOS_EGRESS_EXTERN_QUEUES.COMMENT
    WebUi Label: Comment
    Comment."
  ::= { mGuardQoSEgExternQueueEntry 6 }

-- QOS_EGRESS_EXTERN_QUEUES.MIN_RATE
mGuardQoSEgExtQuMinRate OBJECT-TYPE
  SYNTAX DisplayString
  ACCESS read-write
  STATUS mandatory
  DESCRIPTION
    "Variable name: QOS_EGRESS_EXTERN_QUEUES.MIN_RATE
    WebUi Label: Guaranteed
    Guaranteed rate: >=1 or 'unlimited'."
  ::= { mGuardQoSEgExternQueueEntry 3 }

-- QOS_EGRESS_EXTERN_QUEUES.MAX_RATE
mGuardQoSEgExtQuMaxRate OBJECT-TYPE
  SYNTAX DisplayString
  ACCESS read-write
  STATUS mandatory
  DESCRIPTION
    "Variable name: QOS_EGRESS_EXTERN_QUEUES.MAX_RATE
    WebUi Label: Upper limit
    Guaranteed rate: >=1 or 'unlimited'."
  ::= { mGuardQoSEgExternQueueEntry 4 }

-- QOS_EGRESS_EXTERN_QUEUES.NAME
mGuardQoSEgExtQuName OBJECT-TYPE
  SYNTAX DisplayString
  ACCESS read-write
  STATUS mandatory
  DESCRIPTION
    "Variable name: QOS_EGRESS_EXTERN_QUEUES.NAME
    WebUi Label: Name
    Name of the queue."
  ::= { mGuardQoSEgExternQueueEntry 2 }

-- QOS_EGRESS_EXTERN_QUEUES.PREFERENCE
mGuardQoSEgExtQuPref OBJECT-TYPE
  SYNTAX INTEGER {
    low(1),
    medium(2),
    high(3)
  }
  ACCESS read-write
  STATUS mandatory
  DESCRIPTION
    "Variable name: QOS_EGRESS_EXTERN_QUEUES.PREFERENCE
    WebUi Label: Priority
    Preference of queue."
  ::= { mGuardQoSEgExternQueueEntry 5 }

-- QOS_EGRESS_EXTERN_RATE
mGuardQoSEgExternRate OBJECT-TYPE
  SYNTAX DisplayString
  ACCESS read-write
  STATUS mandatory
  DESCRIPTION
    "Variable name: QOS_EGRESS_EXTERN_RATE
    WebUi Label: Bandwidth
    Rate for egress QoS management: number >= 1 or 'unlimited'."
  ::= { mGuardQoSEgExtern 3 }


-- QOS_EGRESS_EXTERN_RULES table
mGuardQoSEgExternRuleTable OBJECT-TYPE
  SYNTAX SEQUENCE OF MGuardQoSEgExternRuleEntry
  ACCESS not-accessible
  STATUS mandatory
  DESCRIPTION
    "A table of QOS_EGRESS_EXTERN_RULES"
  ::= { mGuardQoSEgExtern 6 }

-- QOS_EGRESS_EXTERN_RULES table entry
mGuardQoSEgExternRuleEntry OBJECT-TYPE
  SYNTAX MGuardQoSEgExternRuleEntry
  ACCESS not-accessible
  STATUS mandatory
  DESCRIPTION
    "An entry of QOS_EGRESS_EXTERN_RULES"
  INDEX { mGuardQoSEgExtRuIndex }
  ::= { mGuardQoSEgExternRuleTable 1 }

MGuardQoSEgExternRuleEntry ::= SEQUENCE {
  mGuardQoSEgExtRuIndex                    INTEGER,
  mGuardQoSEgExtRuProto                    INTEGER,
  mGuardQoSEgExtRuSourceIP                 DisplayString,
  mGuardQoSEgExtRuSport                    DisplayString,
  mGuardQoSEgExtRuDestIP                   DisplayString,
  mGuardQoSEgExtRuDport                    DisplayString,
  mGuardQoSEgExtRuFindDSCP                 INTEGER,
  mGuardQoSEgExtRuSetDSCP                  INTEGER,
  mGuardQoSEgExtRuComment                  DisplayString,
  mGuardQoSEgExtRuRowStatus                RowStatus,
  mGuardQoSEgExtRuQRef                     OBJECT IDENTIFIER
}

-- QOS_EGRESS_EXTERN_RULES table index
mGuardQoSEgExtRuIndex OBJECT-TYPE
  SYNTAX INTEGER (1..2147483647)
  ACCESS not-accessible
  STATUS mandatory
  DESCRIPTION
    "Index to QOS_EGRESS_EXTERN_RULES"
  ::= { mGuardQoSEgExternRuleEntry 1 }

-- QOS_EGRESS_EXTERN_RULES row status
mGuardQoSEgExtRuRowStatus OBJECT-TYPE
  SYNTAX RowStatus
  ACCESS read-write
  STATUS mandatory
  DESCRIPTION
    "RowStatus of QOS_EGRESS_EXTERN_RULES"
  ::= { mGuardQoSEgExternRuleEntry 11 }

-- QOS_EGRESS_EXTERN_RULES.COMMENT
mGuardQoSEgExtRuComment OBJECT-TYPE
  SYNTAX DisplayString
  ACCESS read-write
  STATUS mandatory
  DESCRIPTION
    "Variable name: QOS_EGRESS_EXTERN_RULES.COMMENT
    WebUi Label: Comment
    Comment."
  ::= { mGuardQoSEgExternRuleEntry 10 }

-- QOS_EGRESS_EXTERN_RULES.FROM_PORT
mGuardQoSEgExtRuSport OBJECT-TYPE
  SYNTAX DisplayString
  ACCESS read-write
  STATUS mandatory
  DESCRIPTION
    "Variable name: QOS_EGRESS_EXTERN_RULES.FROM_PORT
    WebUi Label: From port
    The rule's source port"
  ::= { mGuardQoSEgExternRuleEntry 4 }

-- QOS_EGRESS_EXTERN_RULES.PROTO
mGuardQoSEgExtRuProto OBJECT-TYPE
  SYNTAX INTEGER {
    icmp(1),
    tcp(6),
    udp(17),
    esp(50),
    all(256)
  }
  ACCESS read-write
  STATUS mandatory
  DESCRIPTION
    "Variable name: QOS_EGRESS_EXTERN_RULES.PROTO
    WebUi Label: Protocol
    The rule's protocol"
  ::= { mGuardQoSEgExternRuleEntry 2 }

-- QOS_EGRESS_EXTERN_RULES.SET_TOSDSCP
mGuardQoSEgExtRuSetDSCP OBJECT-TYPE
  SYNTAX INTEGER {
    tos-normal-service(100),
    tos-minimize-delay(101),
    tos-maximize-throughput(102),
    tos-maximize-reliability(103),
    tos-minimize-cost(104),
    dscp-class-be(200),
    dscp-class-ef(201),
    dscp-class-af11(202),
    dscp-class-af12(203),
    dscp-class-af13(204),
    dscp-class-af21(205),
    dscp-class-af22(206),
    dscp-class-af23(207),
    dscp-class-af31(208),
    dscp-class-af32(209),
    dscp-class-af33(210),
    dscp-class-af41(211),
    dscp-class-af42(212),
    dscp-class-af43(213),
    dscp-class-cs0(300),
    dscp-class-cs1(301),
    dscp-class-cs2(302),
    dscp-class-cs3(303),
    dscp-class-cs4(304),
    dscp-class-cs5(305),
    dscp-class-cs6(306),
    dscp-class-cs7(307),
    dscp-value-0x00(400),
    dscp-value-0x01(401),
    dscp-value-0x02(402),
    dscp-value-0x03(403),
    dscp-value-0x04(404),
    dscp-value-0x05(405),
    dscp-value-0x06(406),
    dscp-value-0x07(407),
    dscp-value-0x08(408),
    dscp-value-0x09(409),
    dscp-value-0x0a(410),
    dscp-value-0x0b(411),
    dscp-value-0x0c(412),
    dscp-value-0x0d(413),
    dscp-value-0x0e(414),
    dscp-value-0x0f(415),
    dscp-value-0x10(416),
    dscp-value-0x11(417),
    dscp-value-0x12(418),
    dscp-value-0x13(419),
    dscp-value-0x14(420),
    dscp-value-0x15(421),
    dscp-value-0x16(422),
    dscp-value-0x17(423),
    dscp-value-0x18(424),
    dscp-value-0x19(425),
    dscp-value-0x1a(426),
    dscp-value-0x1b(427),
    dscp-value-0x1c(428),
    dscp-value-0x1d(429),
    dscp-value-0x1e(430),
    dscp-value-0x1f(431),
    dscp-value-0x20(432),
    dscp-value-0x21(433),
    dscp-value-0x22(434),
    dscp-value-0x23(435),
    dscp-value-0x24(436),
    dscp-value-0x25(437),
    dscp-value-0x26(438),
    dscp-value-0x27(439),
    dscp-value-0x28(440),
    dscp-value-0x29(441),
    dscp-value-0x2a(442),
    dscp-value-0x2b(443),
    dscp-value-0x2c(444),
    dscp-value-0x2d(445),
    dscp-value-0x2e(446),
    dscp-value-0x2f(447),
    dscp-value-0x30(448),
    dscp-value-0x31(449),
    dscp-value-0x32(450),
    dscp-value-0x33(451),
    dscp-value-0x34(452),
    dscp-value-0x35(453),
    dscp-value-0x36(454),
    dscp-value-0x37(455),
    dscp-value-0x38(456),
    dscp-value-0x39(457),
    dscp-value-0x3a(458),
    dscp-value-0x3b(459),
    dscp-value-0x3c(460),
    dscp-value-0x3d(461),
    dscp-value-0x3e(462),
    dscp-value-0x3f(463),
    unchanged(2000)
  }
  ACCESS read-write
  STATUS mandatory
  DESCRIPTION
    "Variable name: QOS_EGRESS_EXTERN_RULES.SET_TOSDSCP
    WebUi Label: New TOS/DSCP
    The rule's target for the DSCP/TOS field"
  ::= { mGuardQoSEgExternRuleEntry 8 }

-- QOS_EGRESS_EXTERN_RULES.FROM_IP
mGuardQoSEgExtRuSourceIP OBJECT-TYPE
  SYNTAX DisplayString
  ACCESS read-write
  STATUS mandatory
  DESCRIPTION
    "Variable name: QOS_EGRESS_EXTERN_RULES.FROM_IP
    WebUi Label: From IP
    The rule's source IP address"
  ::= { mGuardQoSEgExternRuleEntry 3 }

-- QOS_EGRESS_EXTERN_RULES.IN_IP
mGuardQoSEgExtRuDestIP OBJECT-TYPE
  SYNTAX DisplayString
  ACCESS read-write
  STATUS mandatory
  DESCRIPTION
    "Variable name: QOS_EGRESS_EXTERN_RULES.IN_IP
    WebUi Label: To IP
    The rule's destination IP address"
  ::= { mGuardQoSEgExternRuleEntry 5 }

-- QOS_EGRESS_EXTERN_RULES.QUEUE reference
mGuardQoSEgExtRuQRef OBJECT-TYPE
  SYNTAX OBJECT IDENTIFIER
  ACCESS read-write
  STATUS mandatory
  DESCRIPTION
    "Variable name: QOS_EGRESS_EXTERN_RULES.QUEUE
    WebUi Label: Queue name
    When this object contains the OID of an 'mGuardQoSEgExtQuIndex'
    object, the corresponding QoS Egress extern queue is used as the
    rule's target queue."
  ::= { mGuardQoSEgExternRuleEntry 12 }

-- QOS_EGRESS_EXTERN_RULES.FIND_TOSDSCP
mGuardQoSEgExtRuFindDSCP OBJECT-TYPE
  SYNTAX INTEGER {
    tos-normal-service(100),
    tos-minimize-delay(101),
    tos-maximize-throughput(102),
    tos-maximize-reliability(103),
    tos-minimize-cost(104),
    dscp-class-be(200),
    dscp-class-ef(201),
    dscp-class-af11(202),
    dscp-class-af12(203),
    dscp-class-af13(204),
    dscp-class-af21(205),
    dscp-class-af22(206),
    dscp-class-af23(207),
    dscp-class-af31(208),
    dscp-class-af32(209),
    dscp-class-af33(210),
    dscp-class-af41(211),
    dscp-class-af42(212),
    dscp-class-af43(213),
    dscp-class-cs0(300),
    dscp-class-cs1(301),
    dscp-class-cs2(302),
    dscp-class-cs3(303),
    dscp-class-cs4(304),
    dscp-class-cs5(305),
    dscp-class-cs6(306),
    dscp-class-cs7(307),
    dscp-value-0x00(400),
    dscp-value-0x01(401),
    dscp-value-0x02(402),
    dscp-value-0x03(403),
    dscp-value-0x04(404),
    dscp-value-0x05(405),
    dscp-value-0x06(406),
    dscp-value-0x07(407),
    dscp-value-0x08(408),
    dscp-value-0x09(409),
    dscp-value-0x0a(410),
    dscp-value-0x0b(411),
    dscp-value-0x0c(412),
    dscp-value-0x0d(413),
    dscp-value-0x0e(414),
    dscp-value-0x0f(415),
    dscp-value-0x10(416),
    dscp-value-0x11(417),
    dscp-value-0x12(418),
    dscp-value-0x13(419),
    dscp-value-0x14(420),
    dscp-value-0x15(421),
    dscp-value-0x16(422),
    dscp-value-0x17(423),
    dscp-value-0x18(424),
    dscp-value-0x19(425),
    dscp-value-0x1a(426),
    dscp-value-0x1b(427),
    dscp-value-0x1c(428),
    dscp-value-0x1d(429),
    dscp-value-0x1e(430),
    dscp-value-0x1f(431),
    dscp-value-0x20(432),
    dscp-value-0x21(433),
    dscp-value-0x22(434),
    dscp-value-0x23(435),
    dscp-value-0x24(436),
    dscp-value-0x25(437),
    dscp-value-0x26(438),
    dscp-value-0x27(439),
    dscp-value-0x28(440),
    dscp-value-0x29(441),
    dscp-value-0x2a(442),
    dscp-value-0x2b(443),
    dscp-value-0x2c(444),
    dscp-value-0x2d(445),
    dscp-value-0x2e(446),
    dscp-value-0x2f(447),
    dscp-value-0x30(448),
    dscp-value-0x31(449),
    dscp-value-0x32(450),
    dscp-value-0x33(451),
    dscp-value-0x34(452),
    dscp-value-0x35(453),
    dscp-value-0x36(454),
    dscp-value-0x37(455),
    dscp-value-0x38(456),
    dscp-value-0x39(457),
    dscp-value-0x3a(458),
    dscp-value-0x3b(459),
    dscp-value-0x3c(460),
    dscp-value-0x3d(461),
    dscp-value-0x3e(462),
    dscp-value-0x3f(463),
    all(1000),
    tos-not-normal-service(1001),
    dscp-class-not-be(1002),
    dscp-class-not-cs0(1003),
    dscp-value-not-0(1004)
  }
  ACCESS read-write
  STATUS mandatory
  DESCRIPTION
    "Variable name: QOS_EGRESS_EXTERN_RULES.FIND_TOSDSCP
    WebUi Label: Current TOS/DSCP
    The rule's match on the DSCP/TOS field"
  ::= { mGuardQoSEgExternRuleEntry 7 }

-- QOS_EGRESS_EXTERN_RULES.IN_PORT
mGuardQoSEgExtRuDport OBJECT-TYPE
  SYNTAX DisplayString
  ACCESS read-write
  STATUS mandatory
  DESCRIPTION
    "Variable name: QOS_EGRESS_EXTERN_RULES.IN_PORT
    WebUi Label: To port
    The rule's destination port"
  ::= { mGuardQoSEgExternRuleEntry 6 }

-- QOS_EGRESS_EXTERN_UNIT
mGuardQoSEgExternUnit OBJECT-TYPE
  SYNTAX INTEGER {
    kbitpersec(1),
    packetpersec(2)
  }
  ACCESS read-write
  STATUS mandatory
  DESCRIPTION
    "Variable name: QOS_EGRESS_EXTERN_UNIT
    WebUi Label: Measurement unit
    Unit for egress QoS management."
  ::= { mGuardQoSEgExtern 2 }

-- QOS_EGRESS_EXTERN_VPN_DEFAULT reference
mGuardQoSEgVPNExtDefaultQueueRef OBJECT-TYPE
  SYNTAX OBJECT IDENTIFIER
  ACCESS read-write
  STATUS mandatory
  DESCRIPTION
    "Variable name: QOS_EGRESS_EXTERN_VPN_DEFAULT
    WebUi Label: Default queue
    When this object contains the OID of an 'mGuardQoSEgVPNExtQuIndex'
    object, the corresponding QoS Egress VPN extern queue is used as
    default queue."
  ::= { mGuardQoSEgVPNExtern 7 }

-- QOS_EGRESS_EXTERN_VPN_ENABLE
mGuardQoSEgVPNExternEnable OBJECT-TYPE
  SYNTAX INTEGER {
    yes(1),
    no(2)
  }
  ACCESS read-write
  STATUS mandatory
  DESCRIPTION
    "Variable name: QOS_EGRESS_EXTERN_VPN_ENABLE
    WebUi Label: Enable Egress QoS
    Enable egress QoS queuing."
  ::= { mGuardQoSEgVPNExtern 1 }


-- QOS_EGRESS_EXTERN_VPN_QUEUES table
mGuardQoSEgVPNExternQueueTable OBJECT-TYPE
  SYNTAX SEQUENCE OF MGuardQoSEgVPNExternQueueEntry
  ACCESS not-accessible
  STATUS mandatory
  DESCRIPTION
    "A table of QOS_EGRESS_EXTERN_VPN_QUEUES"
  ::= { mGuardQoSEgVPNExtern 4 }

-- QOS_EGRESS_EXTERN_VPN_QUEUES table entry
mGuardQoSEgVPNExternQueueEntry OBJECT-TYPE
  SYNTAX MGuardQoSEgVPNExternQueueEntry
  ACCESS not-accessible
  STATUS mandatory
  DESCRIPTION
    "An entry of QOS_EGRESS_EXTERN_VPN_QUEUES"
  INDEX { mGuardQoSEgVPNExtQuIndex }
  ::= { mGuardQoSEgVPNExternQueueTable 1 }

MGuardQoSEgVPNExternQueueEntry ::= SEQUENCE {
  mGuardQoSEgVPNExtQuIndex                 INTEGER,
  mGuardQoSEgVPNExtQuName                  DisplayString,
  mGuardQoSEgVPNExtQuMinRate               DisplayString,
  mGuardQoSEgVPNExtQuMaxRate               DisplayString,
  mGuardQoSEgVPNExtQuPref                  INTEGER,
  mGuardQoSEgVPNExtQuComment               DisplayString,
  mGuardQoSEgVPNExtQuRowStatus             RowStatus
}

-- QOS_EGRESS_EXTERN_VPN_QUEUES table index
mGuardQoSEgVPNExtQuIndex OBJECT-TYPE
  SYNTAX INTEGER (1..2147483647)
  ACCESS not-accessible
  STATUS mandatory
  DESCRIPTION
    "Index to QOS_EGRESS_EXTERN_VPN_QUEUES"
  ::= { mGuardQoSEgVPNExternQueueEntry 1 }

-- QOS_EGRESS_EXTERN_VPN_QUEUES row status
mGuardQoSEgVPNExtQuRowStatus OBJECT-TYPE
  SYNTAX RowStatus
  ACCESS read-write
  STATUS mandatory
  DESCRIPTION
    "RowStatus of QOS_EGRESS_EXTERN_VPN_QUEUES"
  ::= { mGuardQoSEgVPNExternQueueEntry 7 }

-- QOS_EGRESS_EXTERN_VPN_QUEUES.COMMENT
mGuardQoSEgVPNExtQuComment OBJECT-TYPE
  SYNTAX DisplayString
  ACCESS read-write
  STATUS mandatory
  DESCRIPTION
    "Variable name: QOS_EGRESS_EXTERN_VPN_QUEUES.COMMENT
    WebUi Label: Comment
    Comment."
  ::= { mGuardQoSEgVPNExternQueueEntry 6 }

-- QOS_EGRESS_EXTERN_VPN_QUEUES.MIN_RATE
mGuardQoSEgVPNExtQuMinRate OBJECT-TYPE
  SYNTAX DisplayString
  ACCESS read-write
  STATUS mandatory
  DESCRIPTION
    "Variable name: QOS_EGRESS_EXTERN_VPN_QUEUES.MIN_RATE
    WebUi Label: Guaranteed
    Guaranteed rate: >=1 or 'unlimited'."
  ::= { mGuardQoSEgVPNExternQueueEntry 3 }

-- QOS_EGRESS_EXTERN_VPN_QUEUES.MAX_RATE
mGuardQoSEgVPNExtQuMaxRate OBJECT-TYPE
  SYNTAX DisplayString
  ACCESS read-write
  STATUS mandatory
  DESCRIPTION
    "Variable name: QOS_EGRESS_EXTERN_VPN_QUEUES.MAX_RATE
    WebUi Label: Upper limit
    Guaranteed rate: >=1 or 'unlimited'."
  ::= { mGuardQoSEgVPNExternQueueEntry 4 }

-- QOS_EGRESS_EXTERN_VPN_QUEUES.NAME
mGuardQoSEgVPNExtQuName OBJECT-TYPE
  SYNTAX DisplayString
  ACCESS read-write
  STATUS mandatory
  DESCRIPTION
    "Variable name: QOS_EGRESS_EXTERN_VPN_QUEUES.NAME
    WebUi Label: Name
    Name of the queue."
  ::= { mGuardQoSEgVPNExternQueueEntry 2 }

-- QOS_EGRESS_EXTERN_VPN_QUEUES.PREFERENCE
mGuardQoSEgVPNExtQuPref OBJECT-TYPE
  SYNTAX INTEGER {
    low(1),
    medium(2),
    high(3)
  }
  ACCESS read-write
  STATUS mandatory
  DESCRIPTION
    "Variable name: QOS_EGRESS_EXTERN_VPN_QUEUES.PREFERENCE
    WebUi Label: Priority
    Preference of queue."
  ::= { mGuardQoSEgVPNExternQueueEntry 5 }

-- QOS_EGRESS_EXTERN_VPN_RATE
mGuardQoSEgVPNExternRate OBJECT-TYPE
  SYNTAX DisplayString
  ACCESS read-write
  STATUS mandatory
  DESCRIPTION
    "Variable name: QOS_EGRESS_EXTERN_VPN_RATE
    WebUi Label: Bandwidth
    Rate for egress QoS management: number >= 1 or 'unlimited'."
  ::= { mGuardQoSEgVPNExtern 3 }


-- QOS_EGRESS_EXTERN_VPN_RULES table
mGuardQoSEgVPNExternRuleTable OBJECT-TYPE
  SYNTAX SEQUENCE OF MGuardQoSEgVPNExternRuleEntry
  ACCESS not-accessible
  STATUS mandatory
  DESCRIPTION
    "A table of QOS_EGRESS_EXTERN_VPN_RULES"
  ::= { mGuardQoSEgVPNExtern 6 }

-- QOS_EGRESS_EXTERN_VPN_RULES table entry
mGuardQoSEgVPNExternRuleEntry OBJECT-TYPE
  SYNTAX MGuardQoSEgVPNExternRuleEntry
  ACCESS not-accessible
  STATUS mandatory
  DESCRIPTION
    "An entry of QOS_EGRESS_EXTERN_VPN_RULES"
  INDEX { mGuardQoSEgVPNExtRuIndex }
  ::= { mGuardQoSEgVPNExternRuleTable 1 }

MGuardQoSEgVPNExternRuleEntry ::= SEQUENCE {
  mGuardQoSEgVPNExtRuIndex                 INTEGER,
  mGuardQoSEgVPNExtRuProto                 INTEGER,
  mGuardQoSEgVPNExtRuSourceIP              DisplayString,
  mGuardQoSEgVPNExtRuSport                 DisplayString,
  mGuardQoSEgVPNExtRuDestIP                DisplayString,
  mGuardQoSEgVPNExtRuDport                 DisplayString,
  mGuardQoSEgVPNExtRuFindDSCP              INTEGER,
  mGuardQoSEgVPNExtRuSetDSCP               INTEGER,
  mGuardQoSEgVPNExtRuComment               DisplayString,
  mGuardQoSEgVPNExtRuRowStatus             RowStatus,
  mGuardQoSEgVPNExtRuQRef                  OBJECT IDENTIFIER
}

-- QOS_EGRESS_EXTERN_VPN_RULES table index
mGuardQoSEgVPNExtRuIndex OBJECT-TYPE
  SYNTAX INTEGER (1..2147483647)
  ACCESS not-accessible
  STATUS mandatory
  DESCRIPTION
    "Index to QOS_EGRESS_EXTERN_VPN_RULES"
  ::= { mGuardQoSEgVPNExternRuleEntry 1 }

-- QOS_EGRESS_EXTERN_VPN_RULES row status
mGuardQoSEgVPNExtRuRowStatus OBJECT-TYPE
  SYNTAX RowStatus
  ACCESS read-write
  STATUS mandatory
  DESCRIPTION
    "RowStatus of QOS_EGRESS_EXTERN_VPN_RULES"
  ::= { mGuardQoSEgVPNExternRuleEntry 11 }

-- QOS_EGRESS_EXTERN_VPN_RULES.COMMENT
mGuardQoSEgVPNExtRuComment OBJECT-TYPE
  SYNTAX DisplayString
  ACCESS read-write
  STATUS mandatory
  DESCRIPTION
    "Variable name: QOS_EGRESS_EXTERN_VPN_RULES.COMMENT
    WebUi Label: Comment
    Comment."
  ::= { mGuardQoSEgVPNExternRuleEntry 10 }

-- QOS_EGRESS_EXTERN_VPN_RULES.FROM_PORT
mGuardQoSEgVPNExtRuSport OBJECT-TYPE
  SYNTAX DisplayString
  ACCESS read-write
  STATUS mandatory
  DESCRIPTION
    "Variable name: QOS_EGRESS_EXTERN_VPN_RULES.FROM_PORT
    WebUi Label: From port
    The rule's source port"
  ::= { mGuardQoSEgVPNExternRuleEntry 4 }

-- QOS_EGRESS_EXTERN_VPN_RULES.PROTO
mGuardQoSEgVPNExtRuProto OBJECT-TYPE
  SYNTAX INTEGER {
    icmp(1),
    tcp(6),
    udp(17),
    esp(50),
    all(256)
  }
  ACCESS read-write
  STATUS mandatory
  DESCRIPTION
    "Variable name: QOS_EGRESS_EXTERN_VPN_RULES.PROTO
    WebUi Label: Protocol
    The rule's protocol"
  ::= { mGuardQoSEgVPNExternRuleEntry 2 }

-- QOS_EGRESS_EXTERN_VPN_RULES.SET_TOSDSCP
mGuardQoSEgVPNExtRuSetDSCP OBJECT-TYPE
  SYNTAX INTEGER {
    tos-normal-service(100),
    tos-minimize-delay(101),
    tos-maximize-throughput(102),
    tos-maximize-reliability(103),
    tos-minimize-cost(104),
    dscp-class-be(200),
    dscp-class-ef(201),
    dscp-class-af11(202),
    dscp-class-af12(203),
    dscp-class-af13(204),
    dscp-class-af21(205),
    dscp-class-af22(206),
    dscp-class-af23(207),
    dscp-class-af31(208),
    dscp-class-af32(209),
    dscp-class-af33(210),
    dscp-class-af41(211),
    dscp-class-af42(212),
    dscp-class-af43(213),
    dscp-class-cs0(300),
    dscp-class-cs1(301),
    dscp-class-cs2(302),
    dscp-class-cs3(303),
    dscp-class-cs4(304),
    dscp-class-cs5(305),
    dscp-class-cs6(306),
    dscp-class-cs7(307),
    dscp-value-0x00(400),
    dscp-value-0x01(401),
    dscp-value-0x02(402),
    dscp-value-0x03(403),
    dscp-value-0x04(404),
    dscp-value-0x05(405),
    dscp-value-0x06(406),
    dscp-value-0x07(407),
    dscp-value-0x08(408),
    dscp-value-0x09(409),
    dscp-value-0x0a(410),
    dscp-value-0x0b(411),
    dscp-value-0x0c(412),
    dscp-value-0x0d(413),
    dscp-value-0x0e(414),
    dscp-value-0x0f(415),
    dscp-value-0x10(416),
    dscp-value-0x11(417),
    dscp-value-0x12(418),
    dscp-value-0x13(419),
    dscp-value-0x14(420),
    dscp-value-0x15(421),
    dscp-value-0x16(422),
    dscp-value-0x17(423),
    dscp-value-0x18(424),
    dscp-value-0x19(425),
    dscp-value-0x1a(426),
    dscp-value-0x1b(427),
    dscp-value-0x1c(428),
    dscp-value-0x1d(429),
    dscp-value-0x1e(430),
    dscp-value-0x1f(431),
    dscp-value-0x20(432),
    dscp-value-0x21(433),
    dscp-value-0x22(434),
    dscp-value-0x23(435),
    dscp-value-0x24(436),
    dscp-value-0x25(437),
    dscp-value-0x26(438),
    dscp-value-0x27(439),
    dscp-value-0x28(440),
    dscp-value-0x29(441),
    dscp-value-0x2a(442),
    dscp-value-0x2b(443),
    dscp-value-0x2c(444),
    dscp-value-0x2d(445),
    dscp-value-0x2e(446),
    dscp-value-0x2f(447),
    dscp-value-0x30(448),
    dscp-value-0x31(449),
    dscp-value-0x32(450),
    dscp-value-0x33(451),
    dscp-value-0x34(452),
    dscp-value-0x35(453),
    dscp-value-0x36(454),
    dscp-value-0x37(455),
    dscp-value-0x38(456),
    dscp-value-0x39(457),
    dscp-value-0x3a(458),
    dscp-value-0x3b(459),
    dscp-value-0x3c(460),
    dscp-value-0x3d(461),
    dscp-value-0x3e(462),
    dscp-value-0x3f(463),
    unchanged(2000)
  }
  ACCESS read-write
  STATUS mandatory
  DESCRIPTION
    "Variable name: QOS_EGRESS_EXTERN_VPN_RULES.SET_TOSDSCP
    WebUi Label: New TOS/DSCP
    The rule's target for the DSCP/TOS field"
  ::= { mGuardQoSEgVPNExternRuleEntry 8 }

-- QOS_EGRESS_EXTERN_VPN_RULES.FROM_IP
mGuardQoSEgVPNExtRuSourceIP OBJECT-TYPE
  SYNTAX DisplayString
  ACCESS read-write
  STATUS mandatory
  DESCRIPTION
    "Variable name: QOS_EGRESS_EXTERN_VPN_RULES.FROM_IP
    WebUi Label: From IP
    The rule's source IP address"
  ::= { mGuardQoSEgVPNExternRuleEntry 3 }

-- QOS_EGRESS_EXTERN_VPN_RULES.IN_IP
mGuardQoSEgVPNExtRuDestIP OBJECT-TYPE
  SYNTAX DisplayString
  ACCESS read-write
  STATUS mandatory
  DESCRIPTION
    "Variable name: QOS_EGRESS_EXTERN_VPN_RULES.IN_IP
    WebUi Label: To IP
    The rule's destination IP address"
  ::= { mGuardQoSEgVPNExternRuleEntry 5 }

-- QOS_EGRESS_EXTERN_VPN_RULES.QUEUE reference
mGuardQoSEgVPNExtRuQRef OBJECT-TYPE
  SYNTAX OBJECT IDENTIFIER
  ACCESS read-write
  STATUS mandatory
  DESCRIPTION
    "Variable name: QOS_EGRESS_EXTERN_VPN_RULES.QUEUE
    WebUi Label: Queue name
    When this object contains the OID of an 'mGuardQoSEgVPNExtQuIndex'
    object, the corresponding QoS Egress VPN extern queue is used as the
    rule's target queue."
  ::= { mGuardQoSEgVPNExternRuleEntry 12 }

-- QOS_EGRESS_EXTERN_VPN_RULES.FIND_TOSDSCP
mGuardQoSEgVPNExtRuFindDSCP OBJECT-TYPE
  SYNTAX INTEGER {
    tos-normal-service(100),
    tos-minimize-delay(101),
    tos-maximize-throughput(102),
    tos-maximize-reliability(103),
    tos-minimize-cost(104),
    dscp-class-be(200),
    dscp-class-ef(201),
    dscp-class-af11(202),
    dscp-class-af12(203),
    dscp-class-af13(204),
    dscp-class-af21(205),
    dscp-class-af22(206),
    dscp-class-af23(207),
    dscp-class-af31(208),
    dscp-class-af32(209),
    dscp-class-af33(210),
    dscp-class-af41(211),
    dscp-class-af42(212),
    dscp-class-af43(213),
    dscp-class-cs0(300),
    dscp-class-cs1(301),
    dscp-class-cs2(302),
    dscp-class-cs3(303),
    dscp-class-cs4(304),
    dscp-class-cs5(305),
    dscp-class-cs6(306),
    dscp-class-cs7(307),
    dscp-value-0x00(400),
    dscp-value-0x01(401),
    dscp-value-0x02(402),
    dscp-value-0x03(403),
    dscp-value-0x04(404),
    dscp-value-0x05(405),
    dscp-value-0x06(406),
    dscp-value-0x07(407),
    dscp-value-0x08(408),
    dscp-value-0x09(409),
    dscp-value-0x0a(410),
    dscp-value-0x0b(411),
    dscp-value-0x0c(412),
    dscp-value-0x0d(413),
    dscp-value-0x0e(414),
    dscp-value-0x0f(415),
    dscp-value-0x10(416),
    dscp-value-0x11(417),
    dscp-value-0x12(418),
    dscp-value-0x13(419),
    dscp-value-0x14(420),
    dscp-value-0x15(421),
    dscp-value-0x16(422),
    dscp-value-0x17(423),
    dscp-value-0x18(424),
    dscp-value-0x19(425),
    dscp-value-0x1a(426),
    dscp-value-0x1b(427),
    dscp-value-0x1c(428),
    dscp-value-0x1d(429),
    dscp-value-0x1e(430),
    dscp-value-0x1f(431),
    dscp-value-0x20(432),
    dscp-value-0x21(433),
    dscp-value-0x22(434),
    dscp-value-0x23(435),
    dscp-value-0x24(436),
    dscp-value-0x25(437),
    dscp-value-0x26(438),
    dscp-value-0x27(439),
    dscp-value-0x28(440),
    dscp-value-0x29(441),
    dscp-value-0x2a(442),
    dscp-value-0x2b(443),
    dscp-value-0x2c(444),
    dscp-value-0x2d(445),
    dscp-value-0x2e(446),
    dscp-value-0x2f(447),
    dscp-value-0x30(448),
    dscp-value-0x31(449),
    dscp-value-0x32(450),
    dscp-value-0x33(451),
    dscp-value-0x34(452),
    dscp-value-0x35(453),
    dscp-value-0x36(454),
    dscp-value-0x37(455),
    dscp-value-0x38(456),
    dscp-value-0x39(457),
    dscp-value-0x3a(458),
    dscp-value-0x3b(459),
    dscp-value-0x3c(460),
    dscp-value-0x3d(461),
    dscp-value-0x3e(462),
    dscp-value-0x3f(463),
    all(1000),
    tos-not-normal-service(1001),
    dscp-class-not-be(1002),
    dscp-class-not-cs0(1003),
    dscp-value-not-0(1004)
  }
  ACCESS read-write
  STATUS mandatory
  DESCRIPTION
    "Variable name: QOS_EGRESS_EXTERN_VPN_RULES.FIND_TOSDSCP
    WebUi Label: Current TOS/DSCP
    The rule's match on the DSCP/TOS field"
  ::= { mGuardQoSEgVPNExternRuleEntry 7 }

-- QOS_EGRESS_EXTERN_VPN_RULES.IN_PORT
mGuardQoSEgVPNExtRuDport OBJECT-TYPE
  SYNTAX DisplayString
  ACCESS read-write
  STATUS mandatory
  DESCRIPTION
    "Variable name: QOS_EGRESS_EXTERN_VPN_RULES.IN_PORT
    WebUi Label: To port
    The rule's destination port"
  ::= { mGuardQoSEgVPNExternRuleEntry 6 }

-- QOS_EGRESS_EXTERN_VPN_UNIT
mGuardQoSEgVPNExternUnit OBJECT-TYPE
  SYNTAX INTEGER {
    kbitpersec(1),
    packetpersec(2)
  }
  ACCESS read-write
  STATUS mandatory
  DESCRIPTION
    "Variable name: QOS_EGRESS_EXTERN_VPN_UNIT
    WebUi Label: Measurement unit
    Unit for egress QoS management."
  ::= { mGuardQoSEgVPNExtern 2 }

-- QOS_EGRESS_LOCAL_DEFAULT reference
mGuardQoSEgIntDefaultQueueRef OBJECT-TYPE
  SYNTAX OBJECT IDENTIFIER
  ACCESS read-write
  STATUS mandatory
  DESCRIPTION
    "Variable name: QOS_EGRESS_LOCAL_DEFAULT
    WebUi Label: Default queue
    When this object contains the OID of an 'mGuardQoSEgIntQuIndex'
    object, the corresponding QoS Egress intern queue is used as default
    queue."
  ::= { mGuardQoSEgIntern 7 }

-- QOS_EGRESS_LOCAL_ENABLE
mGuardQoSEgInternEnable OBJECT-TYPE
  SYNTAX INTEGER {
    yes(1),
    no(2)
  }
  ACCESS read-write
  STATUS mandatory
  DESCRIPTION
    "Variable name: QOS_EGRESS_LOCAL_ENABLE
    WebUi Label: Enable Egress QoS
    Enable egress QoS queuing."
  ::= { mGuardQoSEgIntern 1 }


-- QOS_EGRESS_LOCAL_QUEUES table
mGuardQoSEgInternQueueTable OBJECT-TYPE
  SYNTAX SEQUENCE OF MGuardQoSEgInternQueueEntry
  ACCESS not-accessible
  STATUS mandatory
  DESCRIPTION
    "A table of QOS_EGRESS_LOCAL_QUEUES"
  ::= { mGuardQoSEgIntern 4 }

-- QOS_EGRESS_LOCAL_QUEUES table entry
mGuardQoSEgInternQueueEntry OBJECT-TYPE
  SYNTAX MGuardQoSEgInternQueueEntry
  ACCESS not-accessible
  STATUS mandatory
  DESCRIPTION
    "An entry of QOS_EGRESS_LOCAL_QUEUES"
  INDEX { mGuardQoSEgIntQuIndex }
  ::= { mGuardQoSEgInternQueueTable 1 }

MGuardQoSEgInternQueueEntry ::= SEQUENCE {
  mGuardQoSEgIntQuIndex                    INTEGER,
  mGuardQoSEgIntQuName                     DisplayString,
  mGuardQoSEgIntQuMinRate                  DisplayString,
  mGuardQoSEgIntQuMaxRate                  DisplayString,
  mGuardQoSEgIntQuPref                     INTEGER,
  mGuardQoSEgIntQuComment                  DisplayString,
  mGuardQoSEgIntQuRowStatus                RowStatus
}

-- QOS_EGRESS_LOCAL_QUEUES table index
mGuardQoSEgIntQuIndex OBJECT-TYPE
  SYNTAX INTEGER (1..2147483647)
  ACCESS not-accessible
  STATUS mandatory
  DESCRIPTION
    "Index to QOS_EGRESS_LOCAL_QUEUES"
  ::= { mGuardQoSEgInternQueueEntry 1 }

-- QOS_EGRESS_LOCAL_QUEUES row status
mGuardQoSEgIntQuRowStatus OBJECT-TYPE
  SYNTAX RowStatus
  ACCESS read-write
  STATUS mandatory
  DESCRIPTION
    "RowStatus of QOS_EGRESS_LOCAL_QUEUES"
  ::= { mGuardQoSEgInternQueueEntry 7 }

-- QOS_EGRESS_LOCAL_QUEUES.COMMENT
mGuardQoSEgIntQuComment OBJECT-TYPE
  SYNTAX DisplayString
  ACCESS read-write
  STATUS mandatory
  DESCRIPTION
    "Variable name: QOS_EGRESS_LOCAL_QUEUES.COMMENT
    WebUi Label: Comment
    Comment."
  ::= { mGuardQoSEgInternQueueEntry 6 }

-- QOS_EGRESS_LOCAL_QUEUES.MIN_RATE
mGuardQoSEgIntQuMinRate OBJECT-TYPE
  SYNTAX DisplayString
  ACCESS read-write
  STATUS mandatory
  DESCRIPTION
    "Variable name: QOS_EGRESS_LOCAL_QUEUES.MIN_RATE
    WebUi Label: Guaranteed
    Guaranteed rate: >=1 or 'unlimited'."
  ::= { mGuardQoSEgInternQueueEntry 3 }

-- QOS_EGRESS_LOCAL_QUEUES.MAX_RATE
mGuardQoSEgIntQuMaxRate OBJECT-TYPE
  SYNTAX DisplayString
  ACCESS read-write
  STATUS mandatory
  DESCRIPTION
    "Variable name: QOS_EGRESS_LOCAL_QUEUES.MAX_RATE
    WebUi Label: Upper limit
    Guaranteed rate: >=1 or 'unlimited'."
  ::= { mGuardQoSEgInternQueueEntry 4 }

-- QOS_EGRESS_LOCAL_QUEUES.NAME
mGuardQoSEgIntQuName OBJECT-TYPE
  SYNTAX DisplayString
  ACCESS read-write
  STATUS mandatory
  DESCRIPTION
    "Variable name: QOS_EGRESS_LOCAL_QUEUES.NAME
    WebUi Label: Name
    Name of the queue."
  ::= { mGuardQoSEgInternQueueEntry 2 }

-- QOS_EGRESS_LOCAL_QUEUES.PREFERENCE
mGuardQoSEgIntQuPref OBJECT-TYPE
  SYNTAX INTEGER {
    low(1),
    medium(2),
    high(3)
  }
  ACCESS read-write
  STATUS mandatory
  DESCRIPTION
    "Variable name: QOS_EGRESS_LOCAL_QUEUES.PREFERENCE
    WebUi Label: Priority
    Preference of queue."
  ::= { mGuardQoSEgInternQueueEntry 5 }

-- QOS_EGRESS_LOCAL_RATE
mGuardQoSEgInternRate OBJECT-TYPE
  SYNTAX DisplayString
  ACCESS read-write
  STATUS mandatory
  DESCRIPTION
    "Variable name: QOS_EGRESS_LOCAL_RATE
    WebUi Label: Bandwidth
    Rate for egress QoS management: number >= 1 or 'unlimited'."
  ::= { mGuardQoSEgIntern 3 }


-- QOS_EGRESS_LOCAL_RULES table
mGuardQoSEgInternRuleTable OBJECT-TYPE
  SYNTAX SEQUENCE OF MGuardQoSEgInternRuleEntry
  ACCESS not-accessible
  STATUS mandatory
  DESCRIPTION
    "A table of QOS_EGRESS_LOCAL_RULES"
  ::= { mGuardQoSEgIntern 6 }

-- QOS_EGRESS_LOCAL_RULES table entry
mGuardQoSEgInternRuleEntry OBJECT-TYPE
  SYNTAX MGuardQoSEgInternRuleEntry
  ACCESS not-accessible
  STATUS mandatory
  DESCRIPTION
    "An entry of QOS_EGRESS_LOCAL_RULES"
  INDEX { mGuardQoSEgIntRuIndex }
  ::= { mGuardQoSEgInternRuleTable 1 }

MGuardQoSEgInternRuleEntry ::= SEQUENCE {
  mGuardQoSEgIntRuIndex                    INTEGER,
  mGuardQoSEgIntRuProto                    INTEGER,
  mGuardQoSEgIntRuSourceIP                 DisplayString,
  mGuardQoSEgIntRuSport                    DisplayString,
  mGuardQoSEgIntRuDestIP                   DisplayString,
  mGuardQoSEgIntRuDport                    DisplayString,
  mGuardQoSEgIntRuFindDSCP                 INTEGER,
  mGuardQoSEgIntRuSetDSCP                  INTEGER,
  mGuardQoSEgIntRuComment                  DisplayString,
  mGuardQoSEgIntRuRowStatus                RowStatus,
  mGuardQoSEgIntRuQRef                     OBJECT IDENTIFIER
}

-- QOS_EGRESS_LOCAL_RULES table index
mGuardQoSEgIntRuIndex OBJECT-TYPE
  SYNTAX INTEGER (1..2147483647)
  ACCESS not-accessible
  STATUS mandatory
  DESCRIPTION
    "Index to QOS_EGRESS_LOCAL_RULES"
  ::= { mGuardQoSEgInternRuleEntry 1 }

-- QOS_EGRESS_LOCAL_RULES row status
mGuardQoSEgIntRuRowStatus OBJECT-TYPE
  SYNTAX RowStatus
  ACCESS read-write
  STATUS mandatory
  DESCRIPTION
    "RowStatus of QOS_EGRESS_LOCAL_RULES"
  ::= { mGuardQoSEgInternRuleEntry 11 }

-- QOS_EGRESS_LOCAL_RULES.COMMENT
mGuardQoSEgIntRuComment OBJECT-TYPE
  SYNTAX DisplayString
  ACCESS read-write
  STATUS mandatory
  DESCRIPTION
    "Variable name: QOS_EGRESS_LOCAL_RULES.COMMENT
    WebUi Label: Comment
    Comment."
  ::= { mGuardQoSEgInternRuleEntry 10 }

-- QOS_EGRESS_LOCAL_RULES.FROM_PORT
mGuardQoSEgIntRuSport OBJECT-TYPE
  SYNTAX DisplayString
  ACCESS read-write
  STATUS mandatory
  DESCRIPTION
    "Variable name: QOS_EGRESS_LOCAL_RULES.FROM_PORT
    WebUi Label: From port
    The rule's source port"
  ::= { mGuardQoSEgInternRuleEntry 4 }

-- QOS_EGRESS_LOCAL_RULES.PROTO
mGuardQoSEgIntRuProto OBJECT-TYPE
  SYNTAX INTEGER {
    icmp(1),
    tcp(6),
    udp(17),
    esp(50),
    all(256)
  }
  ACCESS read-write
  STATUS mandatory
  DESCRIPTION
    "Variable name: QOS_EGRESS_LOCAL_RULES.PROTO
    WebUi Label: Protocol
    The rule's protocol"
  ::= { mGuardQoSEgInternRuleEntry 2 }

-- QOS_EGRESS_LOCAL_RULES.SET_TOSDSCP
mGuardQoSEgIntRuSetDSCP OBJECT-TYPE
  SYNTAX INTEGER {
    tos-normal-service(100),
    tos-minimize-delay(101),
    tos-maximize-throughput(102),
    tos-maximize-reliability(103),
    tos-minimize-cost(104),
    dscp-class-be(200),
    dscp-class-ef(201),
    dscp-class-af11(202),
    dscp-class-af12(203),
    dscp-class-af13(204),
    dscp-class-af21(205),
    dscp-class-af22(206),
    dscp-class-af23(207),
    dscp-class-af31(208),
    dscp-class-af32(209),
    dscp-class-af33(210),
    dscp-class-af41(211),
    dscp-class-af42(212),
    dscp-class-af43(213),
    dscp-class-cs0(300),
    dscp-class-cs1(301),
    dscp-class-cs2(302),
    dscp-class-cs3(303),
    dscp-class-cs4(304),
    dscp-class-cs5(305),
    dscp-class-cs6(306),
    dscp-class-cs7(307),
    dscp-value-0x00(400),
    dscp-value-0x01(401),
    dscp-value-0x02(402),
    dscp-value-0x03(403),
    dscp-value-0x04(404),
    dscp-value-0x05(405),
    dscp-value-0x06(406),
    dscp-value-0x07(407),
    dscp-value-0x08(408),
    dscp-value-0x09(409),
    dscp-value-0x0a(410),
    dscp-value-0x0b(411),
    dscp-value-0x0c(412),
    dscp-value-0x0d(413),
    dscp-value-0x0e(414),
    dscp-value-0x0f(415),
    dscp-value-0x10(416),
    dscp-value-0x11(417),
    dscp-value-0x12(418),
    dscp-value-0x13(419),
    dscp-value-0x14(420),
    dscp-value-0x15(421),
    dscp-value-0x16(422),
    dscp-value-0x17(423),
    dscp-value-0x18(424),
    dscp-value-0x19(425),
    dscp-value-0x1a(426),
    dscp-value-0x1b(427),
    dscp-value-0x1c(428),
    dscp-value-0x1d(429),
    dscp-value-0x1e(430),
    dscp-value-0x1f(431),
    dscp-value-0x20(432),
    dscp-value-0x21(433),
    dscp-value-0x22(434),
    dscp-value-0x23(435),
    dscp-value-0x24(436),
    dscp-value-0x25(437),
    dscp-value-0x26(438),
    dscp-value-0x27(439),
    dscp-value-0x28(440),
    dscp-value-0x29(441),
    dscp-value-0x2a(442),
    dscp-value-0x2b(443),
    dscp-value-0x2c(444),
    dscp-value-0x2d(445),
    dscp-value-0x2e(446),
    dscp-value-0x2f(447),
    dscp-value-0x30(448),
    dscp-value-0x31(449),
    dscp-value-0x32(450),
    dscp-value-0x33(451),
    dscp-value-0x34(452),
    dscp-value-0x35(453),
    dscp-value-0x36(454),
    dscp-value-0x37(455),
    dscp-value-0x38(456),
    dscp-value-0x39(457),
    dscp-value-0x3a(458),
    dscp-value-0x3b(459),
    dscp-value-0x3c(460),
    dscp-value-0x3d(461),
    dscp-value-0x3e(462),
    dscp-value-0x3f(463),
    unchanged(2000)
  }
  ACCESS read-write
  STATUS mandatory
  DESCRIPTION
    "Variable name: QOS_EGRESS_LOCAL_RULES.SET_TOSDSCP
    WebUi Label: New TOS/DSCP
    The rule's target for the DSCP/TOS field"
  ::= { mGuardQoSEgInternRuleEntry 8 }

-- QOS_EGRESS_LOCAL_RULES.FROM_IP
mGuardQoSEgIntRuSourceIP OBJECT-TYPE
  SYNTAX DisplayString
  ACCESS read-write
  STATUS mandatory
  DESCRIPTION
    "Variable name: QOS_EGRESS_LOCAL_RULES.FROM_IP
    WebUi Label: From IP
    The rule's source IP address"
  ::= { mGuardQoSEgInternRuleEntry 3 }

-- QOS_EGRESS_LOCAL_RULES.IN_IP
mGuardQoSEgIntRuDestIP OBJECT-TYPE
  SYNTAX DisplayString
  ACCESS read-write
  STATUS mandatory
  DESCRIPTION
    "Variable name: QOS_EGRESS_LOCAL_RULES.IN_IP
    WebUi Label: To IP
    The rule's destination IP address"
  ::= { mGuardQoSEgInternRuleEntry 5 }

-- QOS_EGRESS_LOCAL_RULES.QUEUE reference
mGuardQoSEgIntRuQRef OBJECT-TYPE
  SYNTAX OBJECT IDENTIFIER
  ACCESS read-write
  STATUS mandatory
  DESCRIPTION
    "Variable name: QOS_EGRESS_LOCAL_RULES.QUEUE
    WebUi Label: Queue name
    When this object contains the OID of an 'mGuardQoSEgIntQuIndex'
    object, the corresponding QoS Egress intern queue is used as the
    rule's target queue."
  ::= { mGuardQoSEgInternRuleEntry 12 }

-- QOS_EGRESS_LOCAL_RULES.FIND_TOSDSCP
mGuardQoSEgIntRuFindDSCP OBJECT-TYPE
  SYNTAX INTEGER {
    tos-normal-service(100),
    tos-minimize-delay(101),
    tos-maximize-throughput(102),
    tos-maximize-reliability(103),
    tos-minimize-cost(104),
    dscp-class-be(200),
    dscp-class-ef(201),
    dscp-class-af11(202),
    dscp-class-af12(203),
    dscp-class-af13(204),
    dscp-class-af21(205),
    dscp-class-af22(206),
    dscp-class-af23(207),
    dscp-class-af31(208),
    dscp-class-af32(209),
    dscp-class-af33(210),
    dscp-class-af41(211),
    dscp-class-af42(212),
    dscp-class-af43(213),
    dscp-class-cs0(300),
    dscp-class-cs1(301),
    dscp-class-cs2(302),
    dscp-class-cs3(303),
    dscp-class-cs4(304),
    dscp-class-cs5(305),
    dscp-class-cs6(306),
    dscp-class-cs7(307),
    dscp-value-0x00(400),
    dscp-value-0x01(401),
    dscp-value-0x02(402),
    dscp-value-0x03(403),
    dscp-value-0x04(404),
    dscp-value-0x05(405),
    dscp-value-0x06(406),
    dscp-value-0x07(407),
    dscp-value-0x08(408),
    dscp-value-0x09(409),
    dscp-value-0x0a(410),
    dscp-value-0x0b(411),
    dscp-value-0x0c(412),
    dscp-value-0x0d(413),
    dscp-value-0x0e(414),
    dscp-value-0x0f(415),
    dscp-value-0x10(416),
    dscp-value-0x11(417),
    dscp-value-0x12(418),
    dscp-value-0x13(419),
    dscp-value-0x14(420),
    dscp-value-0x15(421),
    dscp-value-0x16(422),
    dscp-value-0x17(423),
    dscp-value-0x18(424),
    dscp-value-0x19(425),
    dscp-value-0x1a(426),
    dscp-value-0x1b(427),
    dscp-value-0x1c(428),
    dscp-value-0x1d(429),
    dscp-value-0x1e(430),
    dscp-value-0x1f(431),
    dscp-value-0x20(432),
    dscp-value-0x21(433),
    dscp-value-0x22(434),
    dscp-value-0x23(435),
    dscp-value-0x24(436),
    dscp-value-0x25(437),
    dscp-value-0x26(438),
    dscp-value-0x27(439),
    dscp-value-0x28(440),
    dscp-value-0x29(441),
    dscp-value-0x2a(442),
    dscp-value-0x2b(443),
    dscp-value-0x2c(444),
    dscp-value-0x2d(445),
    dscp-value-0x2e(446),
    dscp-value-0x2f(447),
    dscp-value-0x30(448),
    dscp-value-0x31(449),
    dscp-value-0x32(450),
    dscp-value-0x33(451),
    dscp-value-0x34(452),
    dscp-value-0x35(453),
    dscp-value-0x36(454),
    dscp-value-0x37(455),
    dscp-value-0x38(456),
    dscp-value-0x39(457),
    dscp-value-0x3a(458),
    dscp-value-0x3b(459),
    dscp-value-0x3c(460),
    dscp-value-0x3d(461),
    dscp-value-0x3e(462),
    dscp-value-0x3f(463),
    all(1000),
    tos-not-normal-service(1001),
    dscp-class-not-be(1002),
    dscp-class-not-cs0(1003),
    dscp-value-not-0(1004)
  }
  ACCESS read-write
  STATUS mandatory
  DESCRIPTION
    "Variable name: QOS_EGRESS_LOCAL_RULES.FIND_TOSDSCP
    WebUi Label: Current TOS/DSCP
    The rule's match on the DSCP/TOS field"
  ::= { mGuardQoSEgInternRuleEntry 7 }

-- QOS_EGRESS_LOCAL_RULES.IN_PORT
mGuardQoSEgIntRuDport OBJECT-TYPE
  SYNTAX DisplayString
  ACCESS read-write
  STATUS mandatory
  DESCRIPTION
    "Variable name: QOS_EGRESS_LOCAL_RULES.IN_PORT
    WebUi Label: To port
    The rule's destination port"
  ::= { mGuardQoSEgInternRuleEntry 6 }

-- QOS_EGRESS_LOCAL_UNIT
mGuardQoSEgInternUnit OBJECT-TYPE
  SYNTAX INTEGER {
    kbitpersec(1),
    packetpersec(2)
  }
  ACCESS read-write
  STATUS mandatory
  DESCRIPTION
    "Variable name: QOS_EGRESS_LOCAL_UNIT
    WebUi Label: Measurement unit
    Unit for egress QoS management."
  ::= { mGuardQoSEgIntern 2 }

-- QOS_EGRESS_LOCAL_VPN_DEFAULT reference
mGuardQoSEgVPNIntDefaultQueueRef OBJECT-TYPE
  SYNTAX OBJECT IDENTIFIER
  ACCESS read-write
  STATUS mandatory
  DESCRIPTION
    "Variable name: QOS_EGRESS_LOCAL_VPN_DEFAULT
    WebUi Label: Default queue
    When this object contains the OID of an 'mGuardQoSEgVPNIntQuIndex'
    object, the corresponding QoS Egress VPN intern queue is used as
    default queue."
  ::= { mGuardQoSEgVPNIntern 7 }

-- QOS_EGRESS_LOCAL_VPN_ENABLE
mGuardQoSEgVPNInternEnable OBJECT-TYPE
  SYNTAX INTEGER {
    yes(1),
    no(2)
  }
  ACCESS read-write
  STATUS mandatory
  DESCRIPTION
    "Variable name: QOS_EGRESS_LOCAL_VPN_ENABLE
    WebUi Label: Enable Egress QoS
    Enable egress QoS queuing."
  ::= { mGuardQoSEgVPNIntern 1 }


-- QOS_EGRESS_LOCAL_VPN_QUEUES table
mGuardQoSEgVPNInternQueueTable OBJECT-TYPE
  SYNTAX SEQUENCE OF MGuardQoSEgVPNInternQueueEntry
  ACCESS not-accessible
  STATUS mandatory
  DESCRIPTION
    "A table of QOS_EGRESS_LOCAL_VPN_QUEUES"
  ::= { mGuardQoSEgVPNIntern 4 }

-- QOS_EGRESS_LOCAL_VPN_QUEUES table entry
mGuardQoSEgVPNInternQueueEntry OBJECT-TYPE
  SYNTAX MGuardQoSEgVPNInternQueueEntry
  ACCESS not-accessible
  STATUS mandatory
  DESCRIPTION
    "An entry of QOS_EGRESS_LOCAL_VPN_QUEUES"
  INDEX { mGuardQoSEgVPNIntQuIndex }
  ::= { mGuardQoSEgVPNInternQueueTable 1 }

MGuardQoSEgVPNInternQueueEntry ::= SEQUENCE {
  mGuardQoSEgVPNIntQuIndex                 INTEGER,
  mGuardQoSEgVPNIntQuName                  DisplayString,
  mGuardQoSEgVPNIntQuMinRate               DisplayString,
  mGuardQoSEgVPNIntQuMaxRate               DisplayString,
  mGuardQoSEgVPNIntQuPref                  INTEGER,
  mGuardQoSEgVPNIntQuComment               DisplayString,
  mGuardQoSEgVPNIntQuRowStatus             RowStatus
}

-- QOS_EGRESS_LOCAL_VPN_QUEUES table index
mGuardQoSEgVPNIntQuIndex OBJECT-TYPE
  SYNTAX INTEGER (1..2147483647)
  ACCESS not-accessible
  STATUS mandatory
  DESCRIPTION
    "Index to QOS_EGRESS_LOCAL_VPN_QUEUES"
  ::= { mGuardQoSEgVPNInternQueueEntry 1 }

-- QOS_EGRESS_LOCAL_VPN_QUEUES row status
mGuardQoSEgVPNIntQuRowStatus OBJECT-TYPE
  SYNTAX RowStatus
  ACCESS read-write
  STATUS mandatory
  DESCRIPTION
    "RowStatus of QOS_EGRESS_LOCAL_VPN_QUEUES"
  ::= { mGuardQoSEgVPNInternQueueEntry 7 }

-- QOS_EGRESS_LOCAL_VPN_QUEUES.COMMENT
mGuardQoSEgVPNIntQuComment OBJECT-TYPE
  SYNTAX DisplayString
  ACCESS read-write
  STATUS mandatory
  DESCRIPTION
    "Variable name: QOS_EGRESS_LOCAL_VPN_QUEUES.COMMENT
    WebUi Label: Comment
    Comment."
  ::= { mGuardQoSEgVPNInternQueueEntry 6 }

-- QOS_EGRESS_LOCAL_VPN_QUEUES.MIN_RATE
mGuardQoSEgVPNIntQuMinRate OBJECT-TYPE
  SYNTAX DisplayString
  ACCESS read-write
  STATUS mandatory
  DESCRIPTION
    "Variable name: QOS_EGRESS_LOCAL_VPN_QUEUES.MIN_RATE
    WebUi Label: Guaranteed
    Guaranteed rate: >=1 or 'unlimited'."
  ::= { mGuardQoSEgVPNInternQueueEntry 3 }

-- QOS_EGRESS_LOCAL_VPN_QUEUES.MAX_RATE
mGuardQoSEgVPNIntQuMaxRate OBJECT-TYPE
  SYNTAX DisplayString
  ACCESS read-write
  STATUS mandatory
  DESCRIPTION
    "Variable name: QOS_EGRESS_LOCAL_VPN_QUEUES.MAX_RATE
    WebUi Label: Upper limit
    Guaranteed rate: >=1 or 'unlimited'."
  ::= { mGuardQoSEgVPNInternQueueEntry 4 }

-- QOS_EGRESS_LOCAL_VPN_QUEUES.NAME
mGuardQoSEgVPNIntQuName OBJECT-TYPE
  SYNTAX DisplayString
  ACCESS read-write
  STATUS mandatory
  DESCRIPTION
    "Variable name: QOS_EGRESS_LOCAL_VPN_QUEUES.NAME
    WebUi Label: Name
    Name of the queue."
  ::= { mGuardQoSEgVPNInternQueueEntry 2 }

-- QOS_EGRESS_LOCAL_VPN_QUEUES.PREFERENCE
mGuardQoSEgVPNIntQuPref OBJECT-TYPE
  SYNTAX INTEGER {
    low(1),
    medium(2),
    high(3)
  }
  ACCESS read-write
  STATUS mandatory
  DESCRIPTION
    "Variable name: QOS_EGRESS_LOCAL_VPN_QUEUES.PREFERENCE
    WebUi Label: Priority
    Preference of queue."
  ::= { mGuardQoSEgVPNInternQueueEntry 5 }

-- QOS_EGRESS_LOCAL_VPN_RATE
mGuardQoSEgVPNInternRate OBJECT-TYPE
  SYNTAX DisplayString
  ACCESS read-write
  STATUS mandatory
  DESCRIPTION
    "Variable name: QOS_EGRESS_LOCAL_VPN_RATE
    WebUi Label: Bandwidth
    Rate for egress QoS management: number >= 1 or 'unlimited'."
  ::= { mGuardQoSEgVPNIntern 3 }


-- QOS_EGRESS_LOCAL_VPN_RULES table
mGuardQoSEgVPNInternRuleTable OBJECT-TYPE
  SYNTAX SEQUENCE OF MGuardQoSEgVPNInternRuleEntry
  ACCESS not-accessible
  STATUS mandatory
  DESCRIPTION
    "A table of QOS_EGRESS_LOCAL_VPN_RULES"
  ::= { mGuardQoSEgVPNIntern 6 }

-- QOS_EGRESS_LOCAL_VPN_RULES table entry
mGuardQoSEgVPNInternRuleEntry OBJECT-TYPE
  SYNTAX MGuardQoSEgVPNInternRuleEntry
  ACCESS not-accessible
  STATUS mandatory
  DESCRIPTION
    "An entry of QOS_EGRESS_LOCAL_VPN_RULES"
  INDEX { mGuardQoSEgVPNIntRuIndex }
  ::= { mGuardQoSEgVPNInternRuleTable 1 }

MGuardQoSEgVPNInternRuleEntry ::= SEQUENCE {
  mGuardQoSEgVPNIntRuIndex                 INTEGER,
  mGuardQoSEgVPNIntRuProto                 INTEGER,
  mGuardQoSEgVPNIntRuSourceIP              DisplayString,
  mGuardQoSEgVPNIntRuSport                 DisplayString,
  mGuardQoSEgVPNIntRuDestIP                DisplayString,
  mGuardQoSEgVPNIntRuDport                 DisplayString,
  mGuardQoSEgVPNIntRuFindDSCP              INTEGER,
  mGuardQoSEgVPNIntRuSetDSCP               INTEGER,
  mGuardQoSEgVPNIntRuComment               DisplayString,
  mGuardQoSEgVPNIntRuRowStatus             RowStatus,
  mGuardQoSEgVPNIntRuQRef                  OBJECT IDENTIFIER
}

-- QOS_EGRESS_LOCAL_VPN_RULES table index
mGuardQoSEgVPNIntRuIndex OBJECT-TYPE
  SYNTAX INTEGER (1..2147483647)
  ACCESS not-accessible
  STATUS mandatory
  DESCRIPTION
    "Index to QOS_EGRESS_LOCAL_VPN_RULES"
  ::= { mGuardQoSEgVPNInternRuleEntry 1 }

-- QOS_EGRESS_LOCAL_VPN_RULES row status
mGuardQoSEgVPNIntRuRowStatus OBJECT-TYPE
  SYNTAX RowStatus
  ACCESS read-write
  STATUS mandatory
  DESCRIPTION
    "RowStatus of QOS_EGRESS_LOCAL_VPN_RULES"
  ::= { mGuardQoSEgVPNInternRuleEntry 11 }

-- QOS_EGRESS_LOCAL_VPN_RULES.COMMENT
mGuardQoSEgVPNIntRuComment OBJECT-TYPE
  SYNTAX DisplayString
  ACCESS read-write
  STATUS mandatory
  DESCRIPTION
    "Variable name: QOS_EGRESS_LOCAL_VPN_RULES.COMMENT
    WebUi Label: Comment
    Comment."
  ::= { mGuardQoSEgVPNInternRuleEntry 10 }

-- QOS_EGRESS_LOCAL_VPN_RULES.FROM_PORT
mGuardQoSEgVPNIntRuSport OBJECT-TYPE
  SYNTAX DisplayString
  ACCESS read-write
  STATUS mandatory
  DESCRIPTION
    "Variable name: QOS_EGRESS_LOCAL_VPN_RULES.FROM_PORT
    WebUi Label: From port
    The rule's source port"
  ::= { mGuardQoSEgVPNInternRuleEntry 4 }

-- QOS_EGRESS_LOCAL_VPN_RULES.PROTO
mGuardQoSEgVPNIntRuProto OBJECT-TYPE
  SYNTAX INTEGER {
    icmp(1),
    tcp(6),
    udp(17),
    esp(50),
    all(256)
  }
  ACCESS read-write
  STATUS mandatory
  DESCRIPTION
    "Variable name: QOS_EGRESS_LOCAL_VPN_RULES.PROTO
    WebUi Label: Protocol
    The rule's protocol"
  ::= { mGuardQoSEgVPNInternRuleEntry 2 }

-- QOS_EGRESS_LOCAL_VPN_RULES.SET_TOSDSCP
mGuardQoSEgVPNIntRuSetDSCP OBJECT-TYPE
  SYNTAX INTEGER {
    tos-normal-service(100),
    tos-minimize-delay(101),
    tos-maximize-throughput(102),
    tos-maximize-reliability(103),
    tos-minimize-cost(104),
    dscp-class-be(200),
    dscp-class-ef(201),
    dscp-class-af11(202),
    dscp-class-af12(203),
    dscp-class-af13(204),
    dscp-class-af21(205),
    dscp-class-af22(206),
    dscp-class-af23(207),
    dscp-class-af31(208),
    dscp-class-af32(209),
    dscp-class-af33(210),
    dscp-class-af41(211),
    dscp-class-af42(212),
    dscp-class-af43(213),
    dscp-class-cs0(300),
    dscp-class-cs1(301),
    dscp-class-cs2(302),
    dscp-class-cs3(303),
    dscp-class-cs4(304),
    dscp-class-cs5(305),
    dscp-class-cs6(306),
    dscp-class-cs7(307),
    dscp-value-0x00(400),
    dscp-value-0x01(401),
    dscp-value-0x02(402),
    dscp-value-0x03(403),
    dscp-value-0x04(404),
    dscp-value-0x05(405),
    dscp-value-0x06(406),
    dscp-value-0x07(407),
    dscp-value-0x08(408),
    dscp-value-0x09(409),
    dscp-value-0x0a(410),
    dscp-value-0x0b(411),
    dscp-value-0x0c(412),
    dscp-value-0x0d(413),
    dscp-value-0x0e(414),
    dscp-value-0x0f(415),
    dscp-value-0x10(416),
    dscp-value-0x11(417),
    dscp-value-0x12(418),
    dscp-value-0x13(419),
    dscp-value-0x14(420),
    dscp-value-0x15(421),
    dscp-value-0x16(422),
    dscp-value-0x17(423),
    dscp-value-0x18(424),
    dscp-value-0x19(425),
    dscp-value-0x1a(426),
    dscp-value-0x1b(427),
    dscp-value-0x1c(428),
    dscp-value-0x1d(429),
    dscp-value-0x1e(430),
    dscp-value-0x1f(431),
    dscp-value-0x20(432),
    dscp-value-0x21(433),
    dscp-value-0x22(434),
    dscp-value-0x23(435),
    dscp-value-0x24(436),
    dscp-value-0x25(437),
    dscp-value-0x26(438),
    dscp-value-0x27(439),
    dscp-value-0x28(440),
    dscp-value-0x29(441),
    dscp-value-0x2a(442),
    dscp-value-0x2b(443),
    dscp-value-0x2c(444),
    dscp-value-0x2d(445),
    dscp-value-0x2e(446),
    dscp-value-0x2f(447),
    dscp-value-0x30(448),
    dscp-value-0x31(449),
    dscp-value-0x32(450),
    dscp-value-0x33(451),
    dscp-value-0x34(452),
    dscp-value-0x35(453),
    dscp-value-0x36(454),
    dscp-value-0x37(455),
    dscp-value-0x38(456),
    dscp-value-0x39(457),
    dscp-value-0x3a(458),
    dscp-value-0x3b(459),
    dscp-value-0x3c(460),
    dscp-value-0x3d(461),
    dscp-value-0x3e(462),
    dscp-value-0x3f(463),
    unchanged(2000)
  }
  ACCESS read-write
  STATUS mandatory
  DESCRIPTION
    "Variable name: QOS_EGRESS_LOCAL_VPN_RULES.SET_TOSDSCP
    WebUi Label: New TOS/DSCP
    The rule's target for the DSCP/TOS field"
  ::= { mGuardQoSEgVPNInternRuleEntry 8 }

-- QOS_EGRESS_LOCAL_VPN_RULES.FROM_IP
mGuardQoSEgVPNIntRuSourceIP OBJECT-TYPE
  SYNTAX DisplayString
  ACCESS read-write
  STATUS mandatory
  DESCRIPTION
    "Variable name: QOS_EGRESS_LOCAL_VPN_RULES.FROM_IP
    WebUi Label: From IP
    The rule's source IP address"
  ::= { mGuardQoSEgVPNInternRuleEntry 3 }

-- QOS_EGRESS_LOCAL_VPN_RULES.IN_IP
mGuardQoSEgVPNIntRuDestIP OBJECT-TYPE
  SYNTAX DisplayString
  ACCESS read-write
  STATUS mandatory
  DESCRIPTION
    "Variable name: QOS_EGRESS_LOCAL_VPN_RULES.IN_IP
    WebUi Label: To IP
    The rule's destination IP address"
  ::= { mGuardQoSEgVPNInternRuleEntry 5 }

-- QOS_EGRESS_LOCAL_VPN_RULES.QUEUE reference
mGuardQoSEgVPNIntRuQRef OBJECT-TYPE
  SYNTAX OBJECT IDENTIFIER
  ACCESS read-write
  STATUS mandatory
  DESCRIPTION
    "Variable name: QOS_EGRESS_LOCAL_VPN_RULES.QUEUE
    WebUi Label: Queue name
    When this object contains the OID of an 'mGuardQoSEgVPNIntQuIndex'
    object, the corresponding QoS Egress VPN intern queue is used as the
    rule's target queue."
  ::= { mGuardQoSEgVPNInternRuleEntry 12 }

-- QOS_EGRESS_LOCAL_VPN_RULES.FIND_TOSDSCP
mGuardQoSEgVPNIntRuFindDSCP OBJECT-TYPE
  SYNTAX INTEGER {
    tos-normal-service(100),
    tos-minimize-delay(101),
    tos-maximize-throughput(102),
    tos-maximize-reliability(103),
    tos-minimize-cost(104),
    dscp-class-be(200),
    dscp-class-ef(201),
    dscp-class-af11(202),
    dscp-class-af12(203),
    dscp-class-af13(204),
    dscp-class-af21(205),
    dscp-class-af22(206),
    dscp-class-af23(207),
    dscp-class-af31(208),
    dscp-class-af32(209),
    dscp-class-af33(210),
    dscp-class-af41(211),
    dscp-class-af42(212),
    dscp-class-af43(213),
    dscp-class-cs0(300),
    dscp-class-cs1(301),
    dscp-class-cs2(302),
    dscp-class-cs3(303),
    dscp-class-cs4(304),
    dscp-class-cs5(305),
    dscp-class-cs6(306),
    dscp-class-cs7(307),
    dscp-value-0x00(400),
    dscp-value-0x01(401),
    dscp-value-0x02(402),
    dscp-value-0x03(403),
    dscp-value-0x04(404),
    dscp-value-0x05(405),
    dscp-value-0x06(406),
    dscp-value-0x07(407),
    dscp-value-0x08(408),
    dscp-value-0x09(409),
    dscp-value-0x0a(410),
    dscp-value-0x0b(411),
    dscp-value-0x0c(412),
    dscp-value-0x0d(413),
    dscp-value-0x0e(414),
    dscp-value-0x0f(415),
    dscp-value-0x10(416),
    dscp-value-0x11(417),
    dscp-value-0x12(418),
    dscp-value-0x13(419),
    dscp-value-0x14(420),
    dscp-value-0x15(421),
    dscp-value-0x16(422),
    dscp-value-0x17(423),
    dscp-value-0x18(424),
    dscp-value-0x19(425),
    dscp-value-0x1a(426),
    dscp-value-0x1b(427),
    dscp-value-0x1c(428),
    dscp-value-0x1d(429),
    dscp-value-0x1e(430),
    dscp-value-0x1f(431),
    dscp-value-0x20(432),
    dscp-value-0x21(433),
    dscp-value-0x22(434),
    dscp-value-0x23(435),
    dscp-value-0x24(436),
    dscp-value-0x25(437),
    dscp-value-0x26(438),
    dscp-value-0x27(439),
    dscp-value-0x28(440),
    dscp-value-0x29(441),
    dscp-value-0x2a(442),
    dscp-value-0x2b(443),
    dscp-value-0x2c(444),
    dscp-value-0x2d(445),
    dscp-value-0x2e(446),
    dscp-value-0x2f(447),
    dscp-value-0x30(448),
    dscp-value-0x31(449),
    dscp-value-0x32(450),
    dscp-value-0x33(451),
    dscp-value-0x34(452),
    dscp-value-0x35(453),
    dscp-value-0x36(454),
    dscp-value-0x37(455),
    dscp-value-0x38(456),
    dscp-value-0x39(457),
    dscp-value-0x3a(458),
    dscp-value-0x3b(459),
    dscp-value-0x3c(460),
    dscp-value-0x3d(461),
    dscp-value-0x3e(462),
    dscp-value-0x3f(463),
    all(1000),
    tos-not-normal-service(1001),
    dscp-class-not-be(1002),
    dscp-class-not-cs0(1003),
    dscp-value-not-0(1004)
  }
  ACCESS read-write
  STATUS mandatory
  DESCRIPTION
    "Variable name: QOS_EGRESS_LOCAL_VPN_RULES.FIND_TOSDSCP
    WebUi Label: Current TOS/DSCP
    The rule's match on the DSCP/TOS field"
  ::= { mGuardQoSEgVPNInternRuleEntry 7 }

-- QOS_EGRESS_LOCAL_VPN_RULES.IN_PORT
mGuardQoSEgVPNIntRuDport OBJECT-TYPE
  SYNTAX DisplayString
  ACCESS read-write
  STATUS mandatory
  DESCRIPTION
    "Variable name: QOS_EGRESS_LOCAL_VPN_RULES.IN_PORT
    WebUi Label: To port
    The rule's destination port"
  ::= { mGuardQoSEgVPNInternRuleEntry 6 }

-- QOS_EGRESS_LOCAL_VPN_UNIT
mGuardQoSEgVPNInternUnit OBJECT-TYPE
  SYNTAX INTEGER {
    kbitpersec(1),
    packetpersec(2)
  }
  ACCESS read-write
  STATUS mandatory
  DESCRIPTION
    "Variable name: QOS_EGRESS_LOCAL_VPN_UNIT
    WebUi Label: Measurement unit
    Unit for egress QoS management."
  ::= { mGuardQoSEgVPNIntern 2 }

-- QOS_INGRESS_EXTERN_ENABLE
mGuardQoSIngExternEnable OBJECT-TYPE
  SYNTAX INTEGER {
    yes(1),
    no(2)
  }
  ACCESS read-write
  STATUS mandatory
  DESCRIPTION
    "Variable name: QOS_INGRESS_EXTERN_ENABLE
    WebUi Label: Enable Ingress QoS
    Enable ingress QoS filtering."
  ::= { mGuardQoSIngExtern 1 }


-- QOS_INGRESS_EXTERN_FILTERS table
mGuardQoSIngExternFilterTable OBJECT-TYPE
  SYNTAX SEQUENCE OF MGuardQoSIngExternFilterEntry
  ACCESS not-accessible
  STATUS mandatory
  DESCRIPTION
    "A table of QOS_INGRESS_EXTERN_FILTERS"
  ::= { mGuardQoSIngExtern 3 }

-- QOS_INGRESS_EXTERN_FILTERS table entry
mGuardQoSIngExternFilterEntry OBJECT-TYPE
  SYNTAX MGuardQoSIngExternFilterEntry
  ACCESS not-accessible
  STATUS mandatory
  DESCRIPTION
    "An entry of QOS_INGRESS_EXTERN_FILTERS"
  INDEX { mGuardQoSIngExtFiIndex }
  ::= { mGuardQoSIngExternFilterTable 1 }

MGuardQoSIngExternFilterEntry ::= SEQUENCE {
  mGuardQoSIngExtFiIndex                   INTEGER,
  mGuardQoSIngExtFiVLANUse                 INTEGER,
  mGuardQoSIngExtFiVLANId                  INTEGER,
  mGuardQoSIngExtFiEthType                 DisplayString,
  mGuardQoSIngExtFiIPProto                 INTEGER,
  mGuardQoSIngExtFiSourceIP                DisplayString,
  mGuardQoSIngExtFiDestIP                  DisplayString,
  mGuardQoSIngExtFiFindDSCP                INTEGER,
  mGuardQoSIngExtFiMinRate                 DisplayString,
  mGuardQoSIngExtFiMaxRate                 DisplayString,
  mGuardQoSIngExtFiBurst                   INTEGER,
  mGuardQoSIngExtFiComment                 DisplayString,
  mGuardQoSIngExtFiRowStatus               RowStatus
}

-- QOS_INGRESS_EXTERN_FILTERS table index
mGuardQoSIngExtFiIndex OBJECT-TYPE
  SYNTAX INTEGER (1..2147483647)
  ACCESS not-accessible
  STATUS mandatory
  DESCRIPTION
    "Index to QOS_INGRESS_EXTERN_FILTERS"
  ::= { mGuardQoSIngExternFilterEntry 1 }

-- QOS_INGRESS_EXTERN_FILTERS row status
mGuardQoSIngExtFiRowStatus OBJECT-TYPE
  SYNTAX RowStatus
  ACCESS read-write
  STATUS mandatory
  DESCRIPTION
    "RowStatus of QOS_INGRESS_EXTERN_FILTERS"
  ::= { mGuardQoSIngExternFilterEntry 13 }

-- QOS_INGRESS_EXTERN_FILTERS.COMMENT
mGuardQoSIngExtFiComment OBJECT-TYPE
  SYNTAX DisplayString
  ACCESS read-write
  STATUS mandatory
  DESCRIPTION
    "Variable name: QOS_INGRESS_EXTERN_FILTERS.COMMENT
    WebUi Label: Comment
    Comment."
  ::= { mGuardQoSIngExternFilterEntry 12 }

-- QOS_INGRESS_EXTERN_FILTERS.MAX_RATE
mGuardQoSIngExtFiMaxRate OBJECT-TYPE
  SYNTAX DisplayString
  ACCESS read-write
  STATUS mandatory
  DESCRIPTION
    "Variable name: QOS_INGRESS_EXTERN_FILTERS.MAX_RATE
    WebUi Label: Upper limit
    Guaranteed rate: >=1 or 'unlimited'."
  ::= { mGuardQoSIngExternFilterEntry 10 }

-- QOS_INGRESS_EXTERN_FILTERS.BURST
mGuardQoSIngExtFiBurst OBJECT-TYPE
  SYNTAX INTEGER(1..1000)
  ACCESS read-write
  STATUS mandatory
  DESCRIPTION
    "Variable name: QOS_INGRESS_EXTERN_FILTERS.BURST
    WebUi Label: Burst
    Burst buffer size."
  ::= { mGuardQoSIngExternFilterEntry 11 }

-- QOS_INGRESS_EXTERN_FILTERS.FROM_IP
mGuardQoSIngExtFiSourceIP OBJECT-TYPE
  SYNTAX DisplayString
  ACCESS read-write
  STATUS mandatory
  DESCRIPTION
    "Variable name: QOS_INGRESS_EXTERN_FILTERS.FROM_IP
    WebUi Label: From IP
    The rule's source IP address"
  ::= { mGuardQoSIngExternFilterEntry 6 }

-- QOS_INGRESS_EXTERN_FILTERS.IN_IP
mGuardQoSIngExtFiDestIP OBJECT-TYPE
  SYNTAX DisplayString
  ACCESS read-write
  STATUS mandatory
  DESCRIPTION
    "Variable name: QOS_INGRESS_EXTERN_FILTERS.IN_IP
    WebUi Label: To IP
    The rule's destination IP address"
  ::= { mGuardQoSIngExternFilterEntry 7 }

-- QOS_INGRESS_EXTERN_FILTERS.MIN_RATE
mGuardQoSIngExtFiMinRate OBJECT-TYPE
  SYNTAX DisplayString
  ACCESS read-write
  STATUS mandatory
  DESCRIPTION
    "Variable name: QOS_INGRESS_EXTERN_FILTERS.MIN_RATE
    WebUi Label: Guaranteed
    Guaranteed rate: >=1 or 'unlimited'."
  ::= { mGuardQoSIngExternFilterEntry 9 }

-- QOS_INGRESS_EXTERN_FILTERS.PROTO
mGuardQoSIngExtFiIPProto OBJECT-TYPE
  SYNTAX INTEGER {
    icmp(1),
    tcp(6),
    udp(17),
    esp(50),
    all(256)
  }
  ACCESS read-write
  STATUS mandatory
  DESCRIPTION
    "Variable name: QOS_INGRESS_EXTERN_FILTERS.PROTO
    WebUi Label: IP protocol
    The rule's IP protocol"
  ::= { mGuardQoSIngExternFilterEntry 5 }

-- QOS_INGRESS_EXTERN_FILTERS.USE_VLAN
mGuardQoSIngExtFiVLANUse OBJECT-TYPE
  SYNTAX INTEGER {
    yes(1),
    no(2)
  }
  ACCESS read-write
  STATUS mandatory
  DESCRIPTION
    "Variable name: QOS_INGRESS_EXTERN_FILTERS.USE_VLAN
    WebUi Label: Use VLAN
    Treat VLAN frames."
  ::= { mGuardQoSIngExternFilterEntry 2 }

-- QOS_INGRESS_EXTERN_FILTERS.FIND_TOSDSCP
mGuardQoSIngExtFiFindDSCP OBJECT-TYPE
  SYNTAX INTEGER {
    tos-normal-service(100),
    tos-minimize-delay(101),
    tos-maximize-throughput(102),
    tos-maximize-reliability(103),
    tos-minimize-cost(104),
    dscp-class-be(200),
    dscp-class-ef(201),
    dscp-class-af11(202),
    dscp-class-af12(203),
    dscp-class-af13(204),
    dscp-class-af21(205),
    dscp-class-af22(206),
    dscp-class-af23(207),
    dscp-class-af31(208),
    dscp-class-af32(209),
    dscp-class-af33(210),
    dscp-class-af41(211),
    dscp-class-af42(212),
    dscp-class-af43(213),
    dscp-class-cs0(300),
    dscp-class-cs1(301),
    dscp-class-cs2(302),
    dscp-class-cs3(303),
    dscp-class-cs4(304),
    dscp-class-cs5(305),
    dscp-class-cs6(306),
    dscp-class-cs7(307),
    dscp-value-0x00(400),
    dscp-value-0x01(401),
    dscp-value-0x02(402),
    dscp-value-0x03(403),
    dscp-value-0x04(404),
    dscp-value-0x05(405),
    dscp-value-0x06(406),
    dscp-value-0x07(407),
    dscp-value-0x08(408),
    dscp-value-0x09(409),
    dscp-value-0x0a(410),
    dscp-value-0x0b(411),
    dscp-value-0x0c(412),
    dscp-value-0x0d(413),
    dscp-value-0x0e(414),
    dscp-value-0x0f(415),
    dscp-value-0x10(416),
    dscp-value-0x11(417),
    dscp-value-0x12(418),
    dscp-value-0x13(419),
    dscp-value-0x14(420),
    dscp-value-0x15(421),
    dscp-value-0x16(422),
    dscp-value-0x17(423),
    dscp-value-0x18(424),
    dscp-value-0x19(425),
    dscp-value-0x1a(426),
    dscp-value-0x1b(427),
    dscp-value-0x1c(428),
    dscp-value-0x1d(429),
    dscp-value-0x1e(430),
    dscp-value-0x1f(431),
    dscp-value-0x20(432),
    dscp-value-0x21(433),
    dscp-value-0x22(434),
    dscp-value-0x23(435),
    dscp-value-0x24(436),
    dscp-value-0x25(437),
    dscp-value-0x26(438),
    dscp-value-0x27(439),
    dscp-value-0x28(440),
    dscp-value-0x29(441),
    dscp-value-0x2a(442),
    dscp-value-0x2b(443),
    dscp-value-0x2c(444),
    dscp-value-0x2d(445),
    dscp-value-0x2e(446),
    dscp-value-0x2f(447),
    dscp-value-0x30(448),
    dscp-value-0x31(449),
    dscp-value-0x32(450),
    dscp-value-0x33(451),
    dscp-value-0x34(452),
    dscp-value-0x35(453),
    dscp-value-0x36(454),
    dscp-value-0x37(455),
    dscp-value-0x38(456),
    dscp-value-0x39(457),
    dscp-value-0x3a(458),
    dscp-value-0x3b(459),
    dscp-value-0x3c(460),
    dscp-value-0x3d(461),
    dscp-value-0x3e(462),
    dscp-value-0x3f(463),
    all(1000),
    tos-not-normal-service(1001),
    dscp-class-not-be(1002),
    dscp-class-not-cs0(1003),
    dscp-value-not-0(1004)
  }
  ACCESS read-write
  STATUS mandatory
  DESCRIPTION
    "Variable name: QOS_INGRESS_EXTERN_FILTERS.FIND_TOSDSCP
    WebUi Label: Current TOS/DSCP
    The rule's match on the DSCP/TOS field"
  ::= { mGuardQoSIngExternFilterEntry 8 }

-- QOS_INGRESS_EXTERN_FILTERS.ETHERTYPE_HEX
mGuardQoSIngExtFiEthType OBJECT-TYPE
  SYNTAX DisplayString
  ACCESS read-write
  STATUS mandatory
  DESCRIPTION
    "Variable name: QOS_INGRESS_EXTERN_FILTERS.ETHERTYPE_HEX
    WebUi Label: Ethernet protocol
    ARP, IPv4 or hex code (without leading 0x)."
  ::= { mGuardQoSIngExternFilterEntry 4 }

-- QOS_INGRESS_EXTERN_FILTERS.VLAN_ID
mGuardQoSIngExtFiVLANId OBJECT-TYPE
  SYNTAX INTEGER(1..4094)
  ACCESS read-write
  STATUS mandatory
  DESCRIPTION
    "Variable name: QOS_INGRESS_EXTERN_FILTERS.VLAN_ID
    WebUi Label: VLAN ID
    VLAN ID to match."
  ::= { mGuardQoSIngExternFilterEntry 3 }

-- QOS_INGRESS_EXTERN_UNIT
mGuardQoSIngExternUnit OBJECT-TYPE
  SYNTAX INTEGER {
    kbitpersec(1),
    packetpersec(2)
  }
  ACCESS read-write
  STATUS mandatory
  DESCRIPTION
    "Variable name: QOS_INGRESS_EXTERN_UNIT
    WebUi Label: Measurement unit
    Unit for ingress filtering."
  ::= { mGuardQoSIngExtern 2 }

-- QOS_INGRESS_LOADTOKEN_MAX
mGuardQoSSupportTokenMax OBJECT-TYPE
  SYNTAX INTEGER(500000001..1000000000)
  ACCESS read-write
  STATUS mandatory
  DESCRIPTION
    "Variable name: QOS_INGRESS_LOADTOKEN_MAX
    WebUi Label: Token upper bound
    Max value for token counter."
  ::= { mGuardQoSSupport 1 }

-- QOS_INGRESS_LOADTOKEN_MIN
mGuardQoSSupportTokenMin OBJECT-TYPE
  SYNTAX INTEGER(1..499999999)
  ACCESS read-write
  STATUS mandatory
  DESCRIPTION
    "Variable name: QOS_INGRESS_LOADTOKEN_MIN
    WebUi Label: Token lower bound
    Min value for token counter."
  ::= { mGuardQoSSupport 2 }

-- QOS_INGRESS_LOADTOKEN_WEIGHT
mGuardQoSSupportTokenWeight OBJECT-TYPE
  SYNTAX INTEGER(0..1024)
  ACCESS read-write
  STATUS mandatory
  DESCRIPTION
    "Variable name: QOS_INGRESS_LOADTOKEN_WEIGHT
    WebUi Label: Refill weight
    Weight value for token counter."
  ::= { mGuardQoSSupport 3 }

-- QOS_INGRESS_LOCAL_ENABLE
mGuardQoSIngInternEnable OBJECT-TYPE
  SYNTAX INTEGER {
    yes(1),
    no(2)
  }
  ACCESS read-write
  STATUS mandatory
  DESCRIPTION
    "Variable name: QOS_INGRESS_LOCAL_ENABLE
    WebUi Label: Enable Ingress QoS
    Enable ingress QoS filtering."
  ::= { mGuardQoSIngIntern 1 }


-- QOS_INGRESS_LOCAL_FILTERS table
mGuardQoSIngInternFilterTable OBJECT-TYPE
  SYNTAX SEQUENCE OF MGuardQoSIngInternFilterEntry
  ACCESS not-accessible
  STATUS mandatory
  DESCRIPTION
    "A table of QOS_INGRESS_LOCAL_FILTERS"
  ::= { mGuardQoSIngIntern 3 }

-- QOS_INGRESS_LOCAL_FILTERS table entry
mGuardQoSIngInternFilterEntry OBJECT-TYPE
  SYNTAX MGuardQoSIngInternFilterEntry
  ACCESS not-accessible
  STATUS mandatory
  DESCRIPTION
    "An entry of QOS_INGRESS_LOCAL_FILTERS"
  INDEX { mGuardQoSIngIntFiIndex }
  ::= { mGuardQoSIngInternFilterTable 1 }

MGuardQoSIngInternFilterEntry ::= SEQUENCE {
  mGuardQoSIngIntFiIndex                   INTEGER,
  mGuardQoSIngIntFiVLANUse                 INTEGER,
  mGuardQoSIngIntFiVLANId                  INTEGER,
  mGuardQoSIngIntFiEthType                 DisplayString,
  mGuardQoSIngIntFiIPProto                 INTEGER,
  mGuardQoSIngIntFiSourceIP                DisplayString,
  mGuardQoSIngIntFiDestIP                  DisplayString,
  mGuardQoSIngIntFiFindDSCP                INTEGER,
  mGuardQoSIngIntFiMinRate                 DisplayString,
  mGuardQoSIngIntFiMaxRate                 DisplayString,
  mGuardQoSIngIntFiBurst                   INTEGER,
  mGuardQoSIngIntFiComment                 DisplayString,
  mGuardQoSIngIntFiRowStatus               RowStatus
}

-- QOS_INGRESS_LOCAL_FILTERS table index
mGuardQoSIngIntFiIndex OBJECT-TYPE
  SYNTAX INTEGER (1..2147483647)
  ACCESS not-accessible
  STATUS mandatory
  DESCRIPTION
    "Index to QOS_INGRESS_LOCAL_FILTERS"
  ::= { mGuardQoSIngInternFilterEntry 1 }

-- QOS_INGRESS_LOCAL_FILTERS row status
mGuardQoSIngIntFiRowStatus OBJECT-TYPE
  SYNTAX RowStatus
  ACCESS read-write
  STATUS mandatory
  DESCRIPTION
    "RowStatus of QOS_INGRESS_LOCAL_FILTERS"
  ::= { mGuardQoSIngInternFilterEntry 13 }

-- QOS_INGRESS_LOCAL_FILTERS.COMMENT
mGuardQoSIngIntFiComment OBJECT-TYPE
  SYNTAX DisplayString
  ACCESS read-write
  STATUS mandatory
  DESCRIPTION
    "Variable name: QOS_INGRESS_LOCAL_FILTERS.COMMENT
    WebUi Label: Comment
    Comment."
  ::= { mGuardQoSIngInternFilterEntry 12 }

-- QOS_INGRESS_LOCAL_FILTERS.MAX_RATE
mGuardQoSIngIntFiMaxRate OBJECT-TYPE
  SYNTAX DisplayString
  ACCESS read-write
  STATUS mandatory
  DESCRIPTION
    "Variable name: QOS_INGRESS_LOCAL_FILTERS.MAX_RATE
    WebUi Label: Upper limit
    Guaranteed rate: >=1 or 'unlimited'."
  ::= { mGuardQoSIngInternFilterEntry 10 }

-- QOS_INGRESS_LOCAL_FILTERS.BURST
mGuardQoSIngIntFiBurst OBJECT-TYPE
  SYNTAX INTEGER(1..1000)
  ACCESS read-write
  STATUS mandatory
  DESCRIPTION
    "Variable name: QOS_INGRESS_LOCAL_FILTERS.BURST
    WebUi Label: Burst
    Burst buffer size."
  ::= { mGuardQoSIngInternFilterEntry 11 }

-- QOS_INGRESS_LOCAL_FILTERS.FROM_IP
mGuardQoSIngIntFiSourceIP OBJECT-TYPE
  SYNTAX DisplayString
  ACCESS read-write
  STATUS mandatory
  DESCRIPTION
    "Variable name: QOS_INGRESS_LOCAL_FILTERS.FROM_IP
    WebUi Label: From IP
    The rule's source IP address"
  ::= { mGuardQoSIngInternFilterEntry 6 }

-- QOS_INGRESS_LOCAL_FILTERS.IN_IP
mGuardQoSIngIntFiDestIP OBJECT-TYPE
  SYNTAX DisplayString
  ACCESS read-write
  STATUS mandatory
  DESCRIPTION
    "Variable name: QOS_INGRESS_LOCAL_FILTERS.IN_IP
    WebUi Label: To IP
    The rule's destination IP address"
  ::= { mGuardQoSIngInternFilterEntry 7 }

-- QOS_INGRESS_LOCAL_FILTERS.MIN_RATE
mGuardQoSIngIntFiMinRate OBJECT-TYPE
  SYNTAX DisplayString
  ACCESS read-write
  STATUS mandatory
  DESCRIPTION
    "Variable name: QOS_INGRESS_LOCAL_FILTERS.MIN_RATE
    WebUi Label: Guaranteed
    Guaranteed rate: >=1 or 'unlimited'."
  ::= { mGuardQoSIngInternFilterEntry 9 }

-- QOS_INGRESS_LOCAL_FILTERS.PROTO
mGuardQoSIngIntFiIPProto OBJECT-TYPE
  SYNTAX INTEGER {
    icmp(1),
    tcp(6),
    udp(17),
    esp(50),
    all(256)
  }
  ACCESS read-write
  STATUS mandatory
  DESCRIPTION
    "Variable name: QOS_INGRESS_LOCAL_FILTERS.PROTO
    WebUi Label: IP protocol
    The rule's IP protocol"
  ::= { mGuardQoSIngInternFilterEntry 5 }

-- QOS_INGRESS_LOCAL_FILTERS.USE_VLAN
mGuardQoSIngIntFiVLANUse OBJECT-TYPE
  SYNTAX INTEGER {
    yes(1),
    no(2)
  }
  ACCESS read-write
  STATUS mandatory
  DESCRIPTION
    "Variable name: QOS_INGRESS_LOCAL_FILTERS.USE_VLAN
    WebUi Label: Use VLAN
    Treat VLAN frames."
  ::= { mGuardQoSIngInternFilterEntry 2 }

-- QOS_INGRESS_LOCAL_FILTERS.FIND_TOSDSCP
mGuardQoSIngIntFiFindDSCP OBJECT-TYPE
  SYNTAX INTEGER {
    tos-normal-service(100),
    tos-minimize-delay(101),
    tos-maximize-throughput(102),
    tos-maximize-reliability(103),
    tos-minimize-cost(104),
    dscp-class-be(200),
    dscp-class-ef(201),
    dscp-class-af11(202),
    dscp-class-af12(203),
    dscp-class-af13(204),
    dscp-class-af21(205),
    dscp-class-af22(206),
    dscp-class-af23(207),
    dscp-class-af31(208),
    dscp-class-af32(209),
    dscp-class-af33(210),
    dscp-class-af41(211),
    dscp-class-af42(212),
    dscp-class-af43(213),
    dscp-class-cs0(300),
    dscp-class-cs1(301),
    dscp-class-cs2(302),
    dscp-class-cs3(303),
    dscp-class-cs4(304),
    dscp-class-cs5(305),
    dscp-class-cs6(306),
    dscp-class-cs7(307),
    dscp-value-0x00(400),
    dscp-value-0x01(401),
    dscp-value-0x02(402),
    dscp-value-0x03(403),
    dscp-value-0x04(404),
    dscp-value-0x05(405),
    dscp-value-0x06(406),
    dscp-value-0x07(407),
    dscp-value-0x08(408),
    dscp-value-0x09(409),
    dscp-value-0x0a(410),
    dscp-value-0x0b(411),
    dscp-value-0x0c(412),
    dscp-value-0x0d(413),
    dscp-value-0x0e(414),
    dscp-value-0x0f(415),
    dscp-value-0x10(416),
    dscp-value-0x11(417),
    dscp-value-0x12(418),
    dscp-value-0x13(419),
    dscp-value-0x14(420),
    dscp-value-0x15(421),
    dscp-value-0x16(422),
    dscp-value-0x17(423),
    dscp-value-0x18(424),
    dscp-value-0x19(425),
    dscp-value-0x1a(426),
    dscp-value-0x1b(427),
    dscp-value-0x1c(428),
    dscp-value-0x1d(429),
    dscp-value-0x1e(430),
    dscp-value-0x1f(431),
    dscp-value-0x20(432),
    dscp-value-0x21(433),
    dscp-value-0x22(434),
    dscp-value-0x23(435),
    dscp-value-0x24(436),
    dscp-value-0x25(437),
    dscp-value-0x26(438),
    dscp-value-0x27(439),
    dscp-value-0x28(440),
    dscp-value-0x29(441),
    dscp-value-0x2a(442),
    dscp-value-0x2b(443),
    dscp-value-0x2c(444),
    dscp-value-0x2d(445),
    dscp-value-0x2e(446),
    dscp-value-0x2f(447),
    dscp-value-0x30(448),
    dscp-value-0x31(449),
    dscp-value-0x32(450),
    dscp-value-0x33(451),
    dscp-value-0x34(452),
    dscp-value-0x35(453),
    dscp-value-0x36(454),
    dscp-value-0x37(455),
    dscp-value-0x38(456),
    dscp-value-0x39(457),
    dscp-value-0x3a(458),
    dscp-value-0x3b(459),
    dscp-value-0x3c(460),
    dscp-value-0x3d(461),
    dscp-value-0x3e(462),
    dscp-value-0x3f(463),
    all(1000),
    tos-not-normal-service(1001),
    dscp-class-not-be(1002),
    dscp-class-not-cs0(1003),
    dscp-value-not-0(1004)
  }
  ACCESS read-write
  STATUS mandatory
  DESCRIPTION
    "Variable name: QOS_INGRESS_LOCAL_FILTERS.FIND_TOSDSCP
    WebUi Label: Current TOS/DSCP
    The rule's match on the DSCP/TOS field"
  ::= { mGuardQoSIngInternFilterEntry 8 }

-- QOS_INGRESS_LOCAL_FILTERS.ETHERTYPE_HEX
mGuardQoSIngIntFiEthType OBJECT-TYPE
  SYNTAX DisplayString
  ACCESS read-write
  STATUS mandatory
  DESCRIPTION
    "Variable name: QOS_INGRESS_LOCAL_FILTERS.ETHERTYPE_HEX
    WebUi Label: Ethernet protocol
    ARP, IPv4 or hex code (without leading 0x)."
  ::= { mGuardQoSIngInternFilterEntry 4 }

-- QOS_INGRESS_LOCAL_FILTERS.VLAN_ID
mGuardQoSIngIntFiVLANId OBJECT-TYPE
  SYNTAX INTEGER(1..4094)
  ACCESS read-write
  STATUS mandatory
  DESCRIPTION
    "Variable name: QOS_INGRESS_LOCAL_FILTERS.VLAN_ID
    WebUi Label: VLAN ID
    VLAN ID to match."
  ::= { mGuardQoSIngInternFilterEntry 3 }

-- QOS_INGRESS_LOCAL_UNIT
mGuardQoSIngInternUnit OBJECT-TYPE
  SYNTAX INTEGER {
    kbitpersec(1),
    packetpersec(2)
  }
  ACCESS read-write
  STATUS mandatory
  DESCRIPTION
    "Variable name: QOS_INGRESS_LOCAL_UNIT
    WebUi Label: Measurement unit
    Unit for ingress filtering."
  ::= { mGuardQoSIngIntern 2 }

-- RADIUS_AUTH_HTTPS_ENABLE
mGuardRADIUSAuthHTTPSEnable OBJECT-TYPE
  SYNTAX INTEGER {
    enable(1),
    disable(2),
    exclusive(3)
  }
  ACCESS read-write
  STATUS mandatory
  DESCRIPTION
    "Variable name: RADIUS_AUTH_HTTPS_ENABLE
    WebUi Label: Enable RADIUS authentication
    Enables or disables RADIUS authentication for administrative access to
    the mGuard via HTTPS: enable / disable / exclusive."
  ::= { mGuardRADIUS 5 }

-- RADIUS_AUTH_SHELL_ENABLE
mGuardRADIUSAuthShellEnable OBJECT-TYPE
  SYNTAX INTEGER {
    enable(1),
    disable(2),
    exclusive(3)
  }
  ACCESS read-write
  STATUS mandatory
  DESCRIPTION
    "Variable name: RADIUS_AUTH_SHELL_ENABLE
    WebUi Label: Use RADIUS authentication for shell access
    Enables or disables RADIUS authentication for administrative access to
    the mGuard via SSH or serial console: enable / disable / exclusive."
  ::= { mGuardRADIUS 6 }


-- RADIUS_FILTER table
mGuardRADIUSFilterTable OBJECT-TYPE
  SYNTAX SEQUENCE OF MGuardRADIUSFilterEntry
  ACCESS not-accessible
  STATUS mandatory
  DESCRIPTION
    "A table of RADIUS_FILTER"
  ::= { mGuardRADIUS 4 }

-- RADIUS_FILTER table entry
mGuardRADIUSFilterEntry OBJECT-TYPE
  SYNTAX MGuardRADIUSFilterEntry
  ACCESS not-accessible
  STATUS mandatory
  DESCRIPTION
    "An entry of RADIUS_FILTER"
  INDEX { mGuardRADIUSFilterIndex }
  ::= { mGuardRADIUSFilterTable 1 }

MGuardRADIUSFilterEntry ::= SEQUENCE {
  mGuardRADIUSFilterIndex                  INTEGER,
  mGuardRADIUSFilterRowStatus              RowStatus,
  mGuardRADIUSFilterFilterID               DisplayString,
  mGuardRADIUSFilterRole                   INTEGER
}

-- RADIUS_FILTER table index
mGuardRADIUSFilterIndex OBJECT-TYPE
  SYNTAX INTEGER (1..2147483647)
  ACCESS not-accessible
  STATUS mandatory
  DESCRIPTION
    "Index to RADIUS_FILTER"
  ::= { mGuardRADIUSFilterEntry 1 }

-- RADIUS_FILTER row status
mGuardRADIUSFilterRowStatus OBJECT-TYPE
  SYNTAX RowStatus
  ACCESS read-write
  STATUS mandatory
  DESCRIPTION
    "RowStatus of RADIUS_FILTER"
  ::= { mGuardRADIUSFilterEntry 2 }

-- RADIUS_FILTER.ROLE
mGuardRADIUSFilterRole OBJECT-TYPE
  SYNTAX INTEGER {
    admin(2),
    netadmin(3),
    audit(4)
  }
  ACCESS read-write
  STATUS mandatory
  DESCRIPTION
    "Variable name: RADIUS_FILTER.ROLE
    WebUi Label: Authorized for access as
    The role admin / netadmin / audit with which the mGuard shall grant
    the user access to it. Please note: 'user' does make sense for access
    via HTTPS only."
  ::= { mGuardRADIUSFilterEntry 4 }

-- RADIUS_FILTER.FILTER_ID
mGuardRADIUSFilterFilterID OBJECT-TYPE
  SYNTAX DisplayString
  ACCESS read-write
  STATUS mandatory
  DESCRIPTION
    "Variable name: RADIUS_FILTER.FILTER_ID
    WebUi Label: Group/Filter ID
    The name of the group which must be contained within the filter
    attribute of a RADIUS reply which authenticates the a user who desires
    access to the mGuard."
  ::= { mGuardRADIUSFilterEntry 3 }

-- RADIUS_NAS
mGuardRADIUSNasIdentifier OBJECT-TYPE
  SYNTAX DisplayString
  ACCESS read-write
  STATUS mandatory
  DESCRIPTION
    "Variable name: RADIUS_NAS
    WebUi Label: RADIUS NAS identifier
    The NAS Identifier used to connect to the RADIUS server."
  ::= { mGuardRADIUS 7 }

-- RADIUS_RETRIES
mGuardRADIUSRetries OBJECT-TYPE
  SYNTAX INTEGER(1..100)
  ACCESS read-write
  STATUS mandatory
  DESCRIPTION
    "Variable name: RADIUS_RETRIES
    WebUi Label: RADIUS retries
    The number of packets of sent to a RADIUS server before giving up."
  ::= { mGuardRADIUS 2 }


-- RADIUS_SERVERS table
mGuardRADIUSServerTable OBJECT-TYPE
  SYNTAX SEQUENCE OF MGuardRADIUSServerEntry
  ACCESS not-accessible
  STATUS mandatory
  DESCRIPTION
    "A table of RADIUS_SERVERS"
  ::= { mGuardRADIUS 3 }

-- RADIUS_SERVERS table entry
mGuardRADIUSServerEntry OBJECT-TYPE
  SYNTAX MGuardRADIUSServerEntry
  ACCESS not-accessible
  STATUS mandatory
  DESCRIPTION
    "An entry of RADIUS_SERVERS"
  INDEX { mGuardRADIUSServerIndex }
  ::= { mGuardRADIUSServerTable 1 }

MGuardRADIUSServerEntry ::= SEQUENCE {
  mGuardRADIUSServerIndex                  INTEGER,
  mGuardRADIUSServerHostname               DisplayString,
  mGuardRADIUSServerPort                   INTEGER,
  mGuardRADIUSServerSecret                 DisplayString,
  mGuardRADIUSServerRowStatus              RowStatus,
  mGuardRADIUSServerPreferVPN              INTEGER
}

-- RADIUS_SERVERS table index
mGuardRADIUSServerIndex OBJECT-TYPE
  SYNTAX INTEGER (1..2147483647)
  ACCESS not-accessible
  STATUS mandatory
  DESCRIPTION
    "Index to RADIUS_SERVERS"
  ::= { mGuardRADIUSServerEntry 1 }

-- RADIUS_SERVERS row status
mGuardRADIUSServerRowStatus OBJECT-TYPE
  SYNTAX RowStatus
  ACCESS read-write
  STATUS mandatory
  DESCRIPTION
    "RowStatus of RADIUS_SERVERS"
  ::= { mGuardRADIUSServerEntry 5 }

-- RADIUS_SERVERS.RADSECRET
mGuardRADIUSServerSecret OBJECT-TYPE
  SYNTAX DisplayString
  ACCESS read-write
  STATUS mandatory
  DESCRIPTION
    "Variable name: RADIUS_SERVERS.RADSECRET
    WebUi Label: Secret
    The secret shared with the RADIUS server."
  ::= { mGuardRADIUSServerEntry 4 }

-- RADIUS_SERVERS.RADSERVER
mGuardRADIUSServerHostname OBJECT-TYPE
  SYNTAX DisplayString
  ACCESS read-write
  STATUS mandatory
  DESCRIPTION
    "Variable name: RADIUS_SERVERS.RADSERVER
    WebUi Label: Server
    The hostname or IP address of the RADIUS server."
  ::= { mGuardRADIUSServerEntry 2 }

-- RADIUS_SERVERS.RAD_PORT
mGuardRADIUSServerPort OBJECT-TYPE
  SYNTAX INTEGER(1..65535)
  ACCESS read-write
  STATUS mandatory
  DESCRIPTION
    "Variable name: RADIUS_SERVERS.RAD_PORT
    WebUi Label: Port
    The port number of the RADIUS server."
  ::= { mGuardRADIUSServerEntry 3 }

-- RADIUS_SERVERS.RAD_PREFER_VPN
mGuardRADIUSServerPreferVPN OBJECT-TYPE
  SYNTAX INTEGER {
    yes(1),
    no(2)
  }
  ACCESS read-write
  STATUS mandatory
  DESCRIPTION
    "Variable name: RADIUS_SERVERS.RAD_PREFER_VPN
    WebUi Label: Via VPN
    Send RADIUS request into a VPN tunnel if the configured RADIUS server
    matches a remote network. yes: send into tunnel (or block if tunnel is
    down) no: ignore tunnel(s) and always send using non-VPN routes."
  ::= { mGuardRADIUSServerEntry 6 }

-- RADIUS_TIMEOUT
mGuardRADIUSTimeout OBJECT-TYPE
  SYNTAX INTEGER(1..100)
  ACCESS read-write
  STATUS mandatory
  DESCRIPTION
    "Variable name: RADIUS_TIMEOUT
    WebUi Label: RADIUS timeout
    Time to wait before deciding that a RADIUS server has not responded to
    a request."
  ::= { mGuardRADIUS 1 }

-- REBOOT_SMS_ENABLE
mGuardRebootSmsEnable OBJECT-TYPE
  SYNTAX INTEGER {
    yes(1),
    no(2)
  }
  ACCESS read-write
  STATUS mandatory
  DESCRIPTION
    "Variable name: REBOOT_SMS_ENABLE
    WebUi Label: Enable reboot via text message
    Enable reboot per SMS (yes, no)"
  ::= { mGuardGsm 29 }

-- REBOOT_SMS_TOKEN
mGuardRebootSmsToken OBJECT-TYPE
  SYNTAX DisplayString
  ACCESS read-write
  STATUS mandatory
  DESCRIPTION
    "Variable name: REBOOT_SMS_TOKEN
    WebUi Label: Token for reboot via text message
    Define a token to reboot the device per SMS."
  ::= { mGuardGsm 30 }

-- REDUNDANCY_AVAIL_EXT_DISABLE
mGuardRRedAvailCheckExtern OBJECT-TYPE
  SYNTAX INTEGER {
    yes(1),
    no(2)
  }
  ACCESS read-write
  STATUS mandatory
  DESCRIPTION
    "Variable name: REDUNDANCY_AVAIL_EXT_DISABLE
    WebUi Label: Disable the availability check at the external interface.
    Perform the availability check at the external network interface."
  ::= { mGuardRouterRedundancy 40 }

-- REDUNDANCY_AVAIL_PASSWORD
mGuardRRedAvailPassword OBJECT-TYPE
  SYNTAX DisplayString
  ACCESS read-write
  STATUS mandatory
  DESCRIPTION
    "Variable name: REDUNDANCY_AVAIL_PASSWORD
    WebUi Label: Passphrase for availability checks
    Password for availability checks for router redundancy."
  ::= { mGuardRouterRedundancy 30 }


-- REDUNDANCY_BRIDGE_PEER_MANAGE table
mGuardRRedBridgePeerIpTable OBJECT-TYPE
  SYNTAX SEQUENCE OF MGuardRRedBridgePeerIpEntry
  ACCESS not-accessible
  STATUS mandatory
  DESCRIPTION
    "A table of REDUNDANCY_BRIDGE_PEER_MANAGE"
  ::= { mGuardRouterRedundancy 43 }

-- REDUNDANCY_BRIDGE_PEER_MANAGE table entry
mGuardRRedBridgePeerIpEntry OBJECT-TYPE
  SYNTAX MGuardRRedBridgePeerIpEntry
  ACCESS not-accessible
  STATUS mandatory
  DESCRIPTION
    "An entry of REDUNDANCY_BRIDGE_PEER_MANAGE"
  INDEX { mGuardRRedBridgePeerIpIndex }
  ::= { mGuardRRedBridgePeerIpTable 1 }

MGuardRRedBridgePeerIpEntry ::= SEQUENCE {
  mGuardRRedBridgePeerIpIndex              INTEGER,
  mGuardRRedBridgePeerIpIP                 IpAddress,
  mGuardRRedBridgePeerIpRowStatus          RowStatus
}

-- REDUNDANCY_BRIDGE_PEER_MANAGE table index
mGuardRRedBridgePeerIpIndex OBJECT-TYPE
  SYNTAX INTEGER (1..2147483647)
  ACCESS not-accessible
  STATUS mandatory
  DESCRIPTION
    "Index to REDUNDANCY_BRIDGE_PEER_MANAGE"
  ::= { mGuardRRedBridgePeerIpEntry 1 }

-- REDUNDANCY_BRIDGE_PEER_MANAGE row status
mGuardRRedBridgePeerIpRowStatus OBJECT-TYPE
  SYNTAX RowStatus
  ACCESS read-write
  STATUS mandatory
  DESCRIPTION
    "RowStatus of REDUNDANCY_BRIDGE_PEER_MANAGE"
  ::= { mGuardRRedBridgePeerIpEntry 3 }

-- REDUNDANCY_BRIDGE_PEER_MANAGE.IP
mGuardRRedBridgePeerIpIP OBJECT-TYPE
  SYNTAX IpAddress
  ACCESS read-write
  STATUS mandatory
  DESCRIPTION
    "Variable name: REDUNDANCY_BRIDGE_PEER_MANAGE.IP
    WebUi Label: IP
    One management IP address of the other mGuard of the HA cluster."
  ::= { mGuardRRedBridgePeerIpEntry 2 }


-- REDUNDANCY_CHECK_HOSTS_PRIM_EXT table
mGuardRRedCheckHostsPrimExtTable OBJECT-TYPE
  SYNTAX SEQUENCE OF MGuardRRedCheckHostsPrimExtEntry
  ACCESS not-accessible
  STATUS mandatory
  DESCRIPTION
    "A table of REDUNDANCY_CHECK_HOSTS_PRIM_EXT"
  ::= { mGuardRouterRedundancy 34 }

-- REDUNDANCY_CHECK_HOSTS_PRIM_EXT table entry
mGuardRRedCheckHostsPrimExtEntry OBJECT-TYPE
  SYNTAX MGuardRRedCheckHostsPrimExtEntry
  ACCESS not-accessible
  STATUS mandatory
  DESCRIPTION
    "An entry of REDUNDANCY_CHECK_HOSTS_PRIM_EXT"
  INDEX { mGuardRRedCheckHostsPrimExtIndex }
  ::= { mGuardRRedCheckHostsPrimExtTable 1 }

MGuardRRedCheckHostsPrimExtEntry ::= SEQUENCE {
  mGuardRRedCheckHostsPrimExtIndex         INTEGER,
  mGuardRRedCheckHostsPrimExtIP            IpAddress,
  mGuardRRedCheckHostsPrimExtRowStatus     RowStatus
}

-- REDUNDANCY_CHECK_HOSTS_PRIM_EXT table index
mGuardRRedCheckHostsPrimExtIndex OBJECT-TYPE
  SYNTAX INTEGER (1..2147483647)
  ACCESS not-accessible
  STATUS mandatory
  DESCRIPTION
    "Index to REDUNDANCY_CHECK_HOSTS_PRIM_EXT"
  ::= { mGuardRRedCheckHostsPrimExtEntry 1 }

-- REDUNDANCY_CHECK_HOSTS_PRIM_EXT row status
mGuardRRedCheckHostsPrimExtRowStatus OBJECT-TYPE
  SYNTAX RowStatus
  ACCESS read-write
  STATUS mandatory
  DESCRIPTION
    "RowStatus of REDUNDANCY_CHECK_HOSTS_PRIM_EXT"
  ::= { mGuardRRedCheckHostsPrimExtEntry 3 }

-- REDUNDANCY_CHECK_HOSTS_PRIM_EXT.IP
mGuardRRedCheckHostsPrimExtIP OBJECT-TYPE
  SYNTAX IpAddress
  ACCESS read-write
  STATUS mandatory
  DESCRIPTION
    "Variable name: REDUNDANCY_CHECK_HOSTS_PRIM_EXT.IP
    WebUi Label: IP
    The allocated IP address"
  ::= { mGuardRRedCheckHostsPrimExtEntry 2 }


-- REDUNDANCY_CHECK_HOSTS_PRIM_INT table
mGuardRRedCheckHostsPrimIntTable OBJECT-TYPE
  SYNTAX SEQUENCE OF MGuardRRedCheckHostsPrimIntEntry
  ACCESS not-accessible
  STATUS mandatory
  DESCRIPTION
    "A table of REDUNDANCY_CHECK_HOSTS_PRIM_INT"
  ::= { mGuardRouterRedundancy 36 }

-- REDUNDANCY_CHECK_HOSTS_PRIM_INT table entry
mGuardRRedCheckHostsPrimIntEntry OBJECT-TYPE
  SYNTAX MGuardRRedCheckHostsPrimIntEntry
  ACCESS not-accessible
  STATUS mandatory
  DESCRIPTION
    "An entry of REDUNDANCY_CHECK_HOSTS_PRIM_INT"
  INDEX { mGuardRRedCheckHostsPrimIntIndex }
  ::= { mGuardRRedCheckHostsPrimIntTable 1 }

MGuardRRedCheckHostsPrimIntEntry ::= SEQUENCE {
  mGuardRRedCheckHostsPrimIntIndex         INTEGER,
  mGuardRRedCheckHostsPrimIntIP            IpAddress,
  mGuardRRedCheckHostsPrimIntRowStatus     RowStatus
}

-- REDUNDANCY_CHECK_HOSTS_PRIM_INT table index
mGuardRRedCheckHostsPrimIntIndex OBJECT-TYPE
  SYNTAX INTEGER (1..2147483647)
  ACCESS not-accessible
  STATUS mandatory
  DESCRIPTION
    "Index to REDUNDANCY_CHECK_HOSTS_PRIM_INT"
  ::= { mGuardRRedCheckHostsPrimIntEntry 1 }

-- REDUNDANCY_CHECK_HOSTS_PRIM_INT row status
mGuardRRedCheckHostsPrimIntRowStatus OBJECT-TYPE
  SYNTAX RowStatus
  ACCESS read-write
  STATUS mandatory
  DESCRIPTION
    "RowStatus of REDUNDANCY_CHECK_HOSTS_PRIM_INT"
  ::= { mGuardRRedCheckHostsPrimIntEntry 3 }

-- REDUNDANCY_CHECK_HOSTS_PRIM_INT.IP
mGuardRRedCheckHostsPrimIntIP OBJECT-TYPE
  SYNTAX IpAddress
  ACCESS read-write
  STATUS mandatory
  DESCRIPTION
    "Variable name: REDUNDANCY_CHECK_HOSTS_PRIM_INT.IP
    WebUi Label: IP
    The allocated IP address"
  ::= { mGuardRRedCheckHostsPrimIntEntry 2 }


-- REDUNDANCY_CHECK_HOSTS_SEC_EXT table
mGuardRRedCheckHostsSecExtTable OBJECT-TYPE
  SYNTAX SEQUENCE OF MGuardRRedCheckHostsSecExtEntry
  ACCESS not-accessible
  STATUS mandatory
  DESCRIPTION
    "A table of REDUNDANCY_CHECK_HOSTS_SEC_EXT"
  ::= { mGuardRouterRedundancy 35 }

-- REDUNDANCY_CHECK_HOSTS_SEC_EXT table entry
mGuardRRedCheckHostsSecExtEntry OBJECT-TYPE
  SYNTAX MGuardRRedCheckHostsSecExtEntry
  ACCESS not-accessible
  STATUS mandatory
  DESCRIPTION
    "An entry of REDUNDANCY_CHECK_HOSTS_SEC_EXT"
  INDEX { mGuardRRedCheckHostsSecExtIndex }
  ::= { mGuardRRedCheckHostsSecExtTable 1 }

MGuardRRedCheckHostsSecExtEntry ::= SEQUENCE {
  mGuardRRedCheckHostsSecExtIndex          INTEGER,
  mGuardRRedCheckHostsSecExtIP             IpAddress,
  mGuardRRedCheckHostsSecExtRowStatus      RowStatus
}

-- REDUNDANCY_CHECK_HOSTS_SEC_EXT table index
mGuardRRedCheckHostsSecExtIndex OBJECT-TYPE
  SYNTAX INTEGER (1..2147483647)
  ACCESS not-accessible
  STATUS mandatory
  DESCRIPTION
    "Index to REDUNDANCY_CHECK_HOSTS_SEC_EXT"
  ::= { mGuardRRedCheckHostsSecExtEntry 1 }

-- REDUNDANCY_CHECK_HOSTS_SEC_EXT row status
mGuardRRedCheckHostsSecExtRowStatus OBJECT-TYPE
  SYNTAX RowStatus
  ACCESS read-write
  STATUS mandatory
  DESCRIPTION
    "RowStatus of REDUNDANCY_CHECK_HOSTS_SEC_EXT"
  ::= { mGuardRRedCheckHostsSecExtEntry 3 }

-- REDUNDANCY_CHECK_HOSTS_SEC_EXT.IP
mGuardRRedCheckHostsSecExtIP OBJECT-TYPE
  SYNTAX IpAddress
  ACCESS read-write
  STATUS mandatory
  DESCRIPTION
    "Variable name: REDUNDANCY_CHECK_HOSTS_SEC_EXT.IP
    WebUi Label: IP
    The allocated IP address"
  ::= { mGuardRRedCheckHostsSecExtEntry 2 }


-- REDUNDANCY_CHECK_HOSTS_SEC_INT table
mGuardRRedCheckHostsSecIntTable OBJECT-TYPE
  SYNTAX SEQUENCE OF MGuardRRedCheckHostsSecIntEntry
  ACCESS not-accessible
  STATUS mandatory
  DESCRIPTION
    "A table of REDUNDANCY_CHECK_HOSTS_SEC_INT"
  ::= { mGuardRouterRedundancy 37 }

-- REDUNDANCY_CHECK_HOSTS_SEC_INT table entry
mGuardRRedCheckHostsSecIntEntry OBJECT-TYPE
  SYNTAX MGuardRRedCheckHostsSecIntEntry
  ACCESS not-accessible
  STATUS mandatory
  DESCRIPTION
    "An entry of REDUNDANCY_CHECK_HOSTS_SEC_INT"
  INDEX { mGuardRRedCheckHostsSecIntIndex }
  ::= { mGuardRRedCheckHostsSecIntTable 1 }

MGuardRRedCheckHostsSecIntEntry ::= SEQUENCE {
  mGuardRRedCheckHostsSecIntIndex          INTEGER,
  mGuardRRedCheckHostsSecIntIP             IpAddress,
  mGuardRRedCheckHostsSecIntRowStatus      RowStatus
}

-- REDUNDANCY_CHECK_HOSTS_SEC_INT table index
mGuardRRedCheckHostsSecIntIndex OBJECT-TYPE
  SYNTAX INTEGER (1..2147483647)
  ACCESS not-accessible
  STATUS mandatory
  DESCRIPTION
    "Index to REDUNDANCY_CHECK_HOSTS_SEC_INT"
  ::= { mGuardRRedCheckHostsSecIntEntry 1 }

-- REDUNDANCY_CHECK_HOSTS_SEC_INT row status
mGuardRRedCheckHostsSecIntRowStatus OBJECT-TYPE
  SYNTAX RowStatus
  ACCESS read-write
  STATUS mandatory
  DESCRIPTION
    "RowStatus of REDUNDANCY_CHECK_HOSTS_SEC_INT"
  ::= { mGuardRRedCheckHostsSecIntEntry 3 }

-- REDUNDANCY_CHECK_HOSTS_SEC_INT.IP
mGuardRRedCheckHostsSecIntIP OBJECT-TYPE
  SYNTAX IpAddress
  ACCESS read-write
  STATUS mandatory
  DESCRIPTION
    "Variable name: REDUNDANCY_CHECK_HOSTS_SEC_INT.IP
    WebUi Label: IP
    The allocated IP address"
  ::= { mGuardRRedCheckHostsSecIntEntry 2 }

-- REDUNDANCY_CHECK_MODE_EXT
mGuardRRedCheckModeExt OBJECT-TYPE
  SYNTAX INTEGER {
    none(1),
    any(2),
    all(3)
  }
  ACCESS read-write
  STATUS mandatory
  DESCRIPTION
    "Variable name: REDUNDANCY_CHECK_MODE_EXT
    WebUi Label: Kind of check
    Operation mode of the redundancy related connectivity check on the
    external interface."
  ::= { mGuardRouterRedundancy 19 }

-- REDUNDANCY_CHECK_MODE_INT
mGuardRRedCheckModeInt OBJECT-TYPE
  SYNTAX INTEGER {
    none(1),
    any(2),
    all(3)
  }
  ACCESS read-write
  STATUS mandatory
  DESCRIPTION
    "Variable name: REDUNDANCY_CHECK_MODE_INT
    WebUi Label: Kind of check
    Operation mode of the redundancy related connectivity check on the
    internal interface."
  ::= { mGuardRouterRedundancy 20 }

-- REDUNDANCY_DAD_ARP_MAC
mGuardRRedDadArpMac OBJECT-TYPE
  SYNTAX MacAddress
  ACCESS read-write
  STATUS mandatory
  DESCRIPTION
    "Variable name: REDUNDANCY_DAD_ARP_MAC
    WebUi Label: Target MAC address for DAD ARP requests
    The MAC address uses as target address for Duplicate Address Detection
    (DAD) ARP requests (see section 4.4.1 of RFC 2131) sent by the mGuard
    for the firewall redundancy feature in stealth mode."
  ::= { mGuardRouterRedundancy 39 }

-- REDUNDANCY_ENABLE
mGuardRouterRedundancyEnable OBJECT-TYPE
  SYNTAX INTEGER {
    yes(1),
    no(2)
  }
  ACCESS read-write
  STATUS mandatory
  DESCRIPTION
    "Variable name: REDUNDANCY_ENABLE
    WebUi Label: Enable redundancy
    Enable Router Redundancy."
  ::= { mGuardRouterRedundancy 1 }

-- REDUNDANCY_FAILOVER_MS
mGuardRRedFailoverMS OBJECT-TYPE
  SYNTAX INTEGER {
    max1000(1000),
    max3000(3000),
    max10000(10000)
  }
  ACCESS read-write
  STATUS mandatory
  DESCRIPTION
    "Variable name: REDUNDANCY_FAILOVER_MS
    WebUi Label: Fail-over switching time
    Maximum allowed time for transition from standby to active redundancy
    state in milliseconds."
  ::= { mGuardRouterRedundancy 15 }

-- REDUNDANCY_ID_BRIDGE
mGuardRRedBridgeID OBJECT-TYPE
  SYNTAX INTEGER(1..255)
  ACCESS read-write
  STATUS mandatory
  DESCRIPTION
    "Variable name: REDUNDANCY_ID_BRIDGE
    WebUi Label: Virtual router ID
    ID of the virtual router in stealth mode."
  ::= { mGuardRouterRedundancy 18 }

-- REDUNDANCY_ID_EXT
mGuardRRedExternalIDNew OBJECT-TYPE
  SYNTAX INTEGER(1..255)
  ACCESS read-write
  STATUS mandatory
  DESCRIPTION
    "Variable name: REDUNDANCY_ID_EXT
    WebUi Label: External virtual router ID
    External ID of the virtual router, replaces
    mGuardRouterRedundancyExternalID."
  ::= { mGuardRouterRedundancy 17 }

-- REDUNDANCY_ID_INT
mGuardRouterRedundancyInternalID OBJECT-TYPE
  SYNTAX INTEGER(1..255)
  ACCESS read-write
  STATUS mandatory
  DESCRIPTION
    "Variable name: REDUNDANCY_ID_INT
    WebUi Label: Internal virtual router ID
    Internal ID of the virtual router."
  ::= { mGuardRouterRedundancy 3 }

-- REDUNDANCY_LATENCY_MS
mGuardRRedLatencyMS OBJECT-TYPE
  SYNTAX INTEGER(0..10000)
  ACCESS read-write
  STATUS mandatory
  DESCRIPTION
    "Variable name: REDUNDANCY_LATENCY_MS
    WebUi Label: Latency before fail-over
    The number of milliseconds during which a device of a redundant pair
    shall ignore the failure of the Availability Check and / or the
    Connectivity Check. If failures are cleared during this time then no
    transition is started at all. Please note: The resolution/precision of
    the system clock may be in the range of several milliseconds. Please
    note: For the Availability Check a failure means that there is no
    active mGuard (to be heard via CARP) and an mGuard which is on standby
    or outdated must become active. But for the Connectivity Check a
    failure means that an mGuard must become faulty."
  ::= { mGuardRouterRedundancy 48 }

-- REDUNDANCY_PRIORITY
mGuardRRedPriorityNew OBJECT-TYPE
  SYNTAX INTEGER {
    low(1),
    high(2)
  }
  ACCESS read-write
  STATUS mandatory
  DESCRIPTION
    "Variable name: REDUNDANCY_PRIORITY
    WebUi Label: Priority of this device
    Priority compared to other redundancy twins, replaces
    mGuardRouterRedundancyPriority."
  ::= { mGuardRouterRedundancy 16 }

-- REDUNDANCY_SYNCIF_ENABLE
mGuardRRedSyncIfEnable OBJECT-TYPE
  SYNTAX INTEGER {
    enabled(1),
    disabled(2)
  }
  ACCESS read-write
  STATUS mandatory
  DESCRIPTION
    "Variable name: REDUNDANCY_SYNCIF_ENABLE
    WebUi Label: Interface which is used for state synchronization
    Enable redundancy state synchronization over a dedicated interface."
  ::= { mGuardRouterRedundancy 23 }

-- REDUNDANCY_SYNCIF_IP
mGuardRRedSyncIfIp OBJECT-TYPE
  SYNTAX IpAddress
  ACCESS read-write
  STATUS mandatory
  DESCRIPTION
    "Variable name: REDUNDANCY_SYNCIF_IP
    WebUi Label: IP
    The IP address of the dedicated interface for redundancy state
    synchronization."
  ::= { mGuardRouterRedundancy 24 }

-- REDUNDANCY_SYNCIF_NET
mGuardRRedSyncIfNet OBJECT-TYPE
  SYNTAX IpAddress
  ACCESS read-write
  STATUS mandatory
  DESCRIPTION
    "Variable name: REDUNDANCY_SYNCIF_NET
    WebUi Label: Netmask
    The IP network mask of the dedicated interface for redundancy state
    synchronization."
  ::= { mGuardRouterRedundancy 38 }

-- REDUNDANCY_SYNCIF_USE_VLAN
mGuardRRedSyncIfUseVLAN OBJECT-TYPE
  SYNTAX INTEGER {
    yes(1),
    no(2)
  }
  ACCESS read-write
  STATUS mandatory
  DESCRIPTION
    "Variable name: REDUNDANCY_SYNCIF_USE_VLAN
    WebUi Label: Use VLAN
    Enable VLAN on a dedicated interface for redundancy."
  ::= { mGuardRouterRedundancy 25 }

-- REDUNDANCY_SYNCIF_VLAN_ID
mGuardRRedSyncIfVLANId OBJECT-TYPE
  SYNTAX INTEGER(1..4094)
  ACCESS read-write
  STATUS mandatory
  DESCRIPTION
    "Variable name: REDUNDANCY_SYNCIF_VLAN_ID
    WebUi Label: VLAN ID
    The VLAN ID of the dedicated interface for redundancy state
    synchronization."
  ::= { mGuardRouterRedundancy 26 }

-- REDUNDANCY_SYNC_ENCR_ALGO
mGuardRRedSyncEncrAlgo OBJECT-TYPE
  SYNTAX INTEGER {
    des(1),
    tripledes168(2),
    aes128(3),
    aes192(4),
    aes256(5),
    proprietaryA(7),
    proprietaryB(8)
  }
  ACCESS read-write
  STATUS mandatory
  DESCRIPTION
    "Variable name: REDUNDANCY_SYNC_ENCR_ALGO
    WebUi Label: Encryption algorithm
    Set encryption algorithm for redundancy state synchronization."
  ::= { mGuardRouterRedundancy 29 }

-- REDUNDANCY_SYNC_ENCR_ENABLE
mGuardRRedSyncEncrEnable OBJECT-TYPE
  SYNTAX INTEGER {
    yes(1),
    no(2)
  }
  ACCESS read-write
  STATUS mandatory
  DESCRIPTION
    "Variable name: REDUNDANCY_SYNC_ENCR_ENABLE
    WebUi Label: Encrypt the state messages
    Enable encryption for redundancy state synchronization."
  ::= { mGuardRouterRedundancy 27 }

-- REDUNDANCY_SYNC_ENCR_HASHALGO
mGuardRRedSyncEncrHashAlgo OBJECT-TYPE
  SYNTAX INTEGER {
    md5(1),
    sha(2),
    sha2-256(3),
    sha2-512(4)
  }
  ACCESS read-write
  STATUS mandatory
  DESCRIPTION
    "Variable name: REDUNDANCY_SYNC_ENCR_HASHALGO
    WebUi Label: Hash algorithm
    Set hash algorithm for redundancy state synchronization."
  ::= { mGuardRouterRedundancy 28 }

-- REDUNDANCY_SYNC_ENCR_PASSWORD
mGuardRRedSyncEncrPassword OBJECT-TYPE
  SYNTAX DisplayString
  ACCESS read-write
  STATUS mandatory
  DESCRIPTION
    "Variable name: REDUNDANCY_SYNC_ENCR_PASSWORD
    WebUi Label: Passphrase
    Passphrase for redundancy state synchronization."
  ::= { mGuardRouterRedundancy 32 }

-- REDUNDANCY_SYNC_VPN_DUMP_RATE
mGuardRRedSyncVPNDumpRate OBJECT-TYPE
  SYNTAX INTEGER(1..500)
  ACCESS read-write
  STATUS mandatory
  DESCRIPTION
    "Variable name: REDUNDANCY_SYNC_VPN_DUMP_RATE
    WebUi Label: VPN States per second
    Maximum number of replicated states per second during a complete dump
    of the VPN state replication for redundancy."
  ::= { mGuardRouterRedundancy 47 }

-- REDUNDANCY_SYNC_VPN_DUMP_RATE_AUTO
mGuardRRedSyncVPNDumpRateAuto OBJECT-TYPE
  SYNTAX INTEGER {
    yes(1),
    no(2)
  }
  ACCESS read-write
  STATUS mandatory
  DESCRIPTION
    "Variable name: REDUNDANCY_SYNC_VPN_DUMP_RATE_AUTO
    WebUi Label: Automatic rate calculation for VPN state replication
    Use automatic calculation or manual specification of the rate of
    states in a VPN state replication dump for redundancy."
  ::= { mGuardRouterRedundancy 46 }


-- REDUNDANCY_VIRT_BRIDGE table
mGuardRRedVirtBridgeTable OBJECT-TYPE
  SYNTAX SEQUENCE OF MGuardRRedVirtBridgeEntry
  ACCESS not-accessible
  STATUS mandatory
  DESCRIPTION
    "A table of REDUNDANCY_VIRT_BRIDGE"
  ::= { mGuardRouterRedundancy 22 }

-- REDUNDANCY_VIRT_BRIDGE table entry
mGuardRRedVirtBridgeEntry OBJECT-TYPE
  SYNTAX MGuardRRedVirtBridgeEntry
  ACCESS not-accessible
  STATUS mandatory
  DESCRIPTION
    "An entry of REDUNDANCY_VIRT_BRIDGE"
  INDEX { mGuardRRedVirtBridgeIndex }
  ::= { mGuardRRedVirtBridgeTable 1 }

MGuardRRedVirtBridgeEntry ::= SEQUENCE {
  mGuardRRedVirtBridgeIndex                INTEGER,
  mGuardRRedVirtBridgeIP                   IpAddress,
  mGuardRRedVirtBridgeRowStatus            RowStatus
}

-- REDUNDANCY_VIRT_BRIDGE table index
mGuardRRedVirtBridgeIndex OBJECT-TYPE
  SYNTAX INTEGER (1..2147483647)
  ACCESS not-accessible
  STATUS mandatory
  DESCRIPTION
    "Index to REDUNDANCY_VIRT_BRIDGE"
  ::= { mGuardRRedVirtBridgeEntry 1 }

-- REDUNDANCY_VIRT_BRIDGE row status
mGuardRRedVirtBridgeRowStatus OBJECT-TYPE
  SYNTAX RowStatus
  ACCESS read-write
  STATUS mandatory
  DESCRIPTION
    "RowStatus of REDUNDANCY_VIRT_BRIDGE"
  ::= { mGuardRRedVirtBridgeEntry 3 }

-- REDUNDANCY_VIRT_BRIDGE.IP
mGuardRRedVirtBridgeIP OBJECT-TYPE
  SYNTAX IpAddress
  ACCESS read-write
  STATUS mandatory
  DESCRIPTION
    "Variable name: REDUNDANCY_VIRT_BRIDGE.IP
    WebUi Label: IP
    One virtual IP address of the HA cluster.n stealth mode"
  ::= { mGuardRRedVirtBridgeEntry 2 }

-- REDUNDANCY_VIRT_BRIDGE_ENABLE
mGuardRRedVirtIpBridgeEnable OBJECT-TYPE
  SYNTAX INTEGER {
    yes(1),
    no(2)
  }
  ACCESS read-write
  STATUS mandatory
  DESCRIPTION
    "Variable name: REDUNDANCY_VIRT_BRIDGE_ENABLE
    WebUi Label: Enable virtual IP
    Enable a virtual IP for redundancy in stealth mode."
  ::= { mGuardRouterRedundancy 21 }


-- REDUNDANCY_VIRT_EXT table
mGuardRRedVirtExtTable OBJECT-TYPE
  SYNTAX SEQUENCE OF MGuardRRedVirtExtEntry
  ACCESS not-accessible
  STATUS mandatory
  DESCRIPTION
    "A table of REDUNDANCY_VIRT_EXT"
  ::= { mGuardRouterRedundancy 41 }

-- REDUNDANCY_VIRT_EXT table entry
mGuardRRedVirtExtEntry OBJECT-TYPE
  SYNTAX MGuardRRedVirtExtEntry
  ACCESS not-accessible
  STATUS mandatory
  DESCRIPTION
    "An entry of REDUNDANCY_VIRT_EXT"
  INDEX { mGuardRRedVirtExtIndex }
  ::= { mGuardRRedVirtExtTable 1 }

MGuardRRedVirtExtEntry ::= SEQUENCE {
  mGuardRRedVirtExtIndex                   INTEGER,
  mGuardRRedVirtExtIP                      IpAddress,
  mGuardRRedVirtExtRowStatus               RowStatus
}

-- REDUNDANCY_VIRT_EXT table index
mGuardRRedVirtExtIndex OBJECT-TYPE
  SYNTAX INTEGER (1..2147483647)
  ACCESS not-accessible
  STATUS mandatory
  DESCRIPTION
    "Index to REDUNDANCY_VIRT_EXT"
  ::= { mGuardRRedVirtExtEntry 1 }

-- REDUNDANCY_VIRT_EXT row status
mGuardRRedVirtExtRowStatus OBJECT-TYPE
  SYNTAX RowStatus
  ACCESS read-write
  STATUS mandatory
  DESCRIPTION
    "RowStatus of REDUNDANCY_VIRT_EXT"
  ::= { mGuardRRedVirtExtEntry 3 }

-- REDUNDANCY_VIRT_EXT.IP
mGuardRRedVirtExtIP OBJECT-TYPE
  SYNTAX IpAddress
  ACCESS read-write
  STATUS mandatory
  DESCRIPTION
    "Variable name: REDUNDANCY_VIRT_EXT.IP
    WebUi Label: IP
    One virtual external IP address of the HA cluster."
  ::= { mGuardRRedVirtExtEntry 2 }


-- REDUNDANCY_VIRT_INT table
mGuardRRedVirtIntTable OBJECT-TYPE
  SYNTAX SEQUENCE OF MGuardRRedVirtIntEntry
  ACCESS not-accessible
  STATUS mandatory
  DESCRIPTION
    "A table of REDUNDANCY_VIRT_INT"
  ::= { mGuardRouterRedundancy 42 }

-- REDUNDANCY_VIRT_INT table entry
mGuardRRedVirtIntEntry OBJECT-TYPE
  SYNTAX MGuardRRedVirtIntEntry
  ACCESS not-accessible
  STATUS mandatory
  DESCRIPTION
    "An entry of REDUNDANCY_VIRT_INT"
  INDEX { mGuardRRedVirtIntIndex }
  ::= { mGuardRRedVirtIntTable 1 }

MGuardRRedVirtIntEntry ::= SEQUENCE {
  mGuardRRedVirtIntIndex                   INTEGER,
  mGuardRRedVirtIntIP                      IpAddress,
  mGuardRRedVirtIntRowStatus               RowStatus
}

-- REDUNDANCY_VIRT_INT table index
mGuardRRedVirtIntIndex OBJECT-TYPE
  SYNTAX INTEGER (1..2147483647)
  ACCESS not-accessible
  STATUS mandatory
  DESCRIPTION
    "Index to REDUNDANCY_VIRT_INT"
  ::= { mGuardRRedVirtIntEntry 1 }

-- REDUNDANCY_VIRT_INT row status
mGuardRRedVirtIntRowStatus OBJECT-TYPE
  SYNTAX RowStatus
  ACCESS read-write
  STATUS mandatory
  DESCRIPTION
    "RowStatus of REDUNDANCY_VIRT_INT"
  ::= { mGuardRRedVirtIntEntry 3 }

-- REDUNDANCY_VIRT_INT.IP
mGuardRRedVirtIntIP OBJECT-TYPE
  SYNTAX IpAddress
  ACCESS read-write
  STATUS mandatory
  DESCRIPTION
    "Variable name: REDUNDANCY_VIRT_INT.IP
    WebUi Label: IP
    One virtual internal IP address of the HA cluster."
  ::= { mGuardRRedVirtIntEntry 2 }


-- REMOTE_CERTS table
mGuardCertsRemoteTable OBJECT-TYPE
  SYNTAX SEQUENCE OF MGuardCertsRemoteEntry
  ACCESS not-accessible
  STATUS mandatory
  DESCRIPTION
    "A table of REMOTE_CERTS"
  ::= { mGuardCertsRemote 1 }

-- REMOTE_CERTS table entry
mGuardCertsRemoteEntry OBJECT-TYPE
  SYNTAX MGuardCertsRemoteEntry
  ACCESS not-accessible
  STATUS mandatory
  DESCRIPTION
    "An entry of REMOTE_CERTS"
  INDEX { mGuardCertsRemoteIndex }
  ::= { mGuardCertsRemoteTable 1 }

MGuardCertsRemoteEntry ::= SEQUENCE {
  mGuardCertsRemoteIndex                   INTEGER,
  mGuardCertsRemoteName                    DisplayString,
  mGuardCertsRemoteCertificate             DisplayString,
  mGuardCertsRemoteRowStatus               RowStatus
}

-- REMOTE_CERTS table index
mGuardCertsRemoteIndex OBJECT-TYPE
  SYNTAX INTEGER (1..2147483647)
  ACCESS not-accessible
  STATUS mandatory
  DESCRIPTION
    "Index to REMOTE_CERTS"
  ::= { mGuardCertsRemoteEntry 1 }

-- REMOTE_CERTS row status
mGuardCertsRemoteRowStatus OBJECT-TYPE
  SYNTAX RowStatus
  ACCESS read-write
  STATUS mandatory
  DESCRIPTION
    "RowStatus of REMOTE_CERTS"
  ::= { mGuardCertsRemoteEntry 50 }

-- REMOTE_CERTS.FRIENDLY_NAME
mGuardCertsRemoteName OBJECT-TYPE
  SYNTAX DisplayString
  ACCESS read-write
  STATUS mandatory
  DESCRIPTION
    "Variable name: REMOTE_CERTS.FRIENDLY_NAME
    WebUi Label: Short name
    A user defined name for the CA certificate, which is also used to
    reference the certificate."
  ::= { mGuardCertsRemoteEntry 2 }

-- REMOTE_CERTS.CERTIFICATE
mGuardCertsRemoteCertificate OBJECT-TYPE
  SYNTAX DisplayString
  ACCESS read-write
  STATUS mandatory
  DESCRIPTION
    "Variable name: REMOTE_CERTS.CERTIFICATE
    WebUi Label: --
    The certificate."
  ::= { mGuardCertsRemoteEntry 3 }

-- ROOT_PASSWORD
mGuardRootPassword OBJECT-TYPE
  SYNTAX DisplayString
  ACCESS read-write
  STATUS mandatory
  DESCRIPTION
    "Variable name: ROOT_PASSWORD
    WebUi Label: Root password
    Changes the password for the user root has access to all system
    resources. Change by setting: <old root password> <new root password>"
  ::= { mGuardPasswords 1 }

-- ROUTER_MODE
mGuardRouterMode OBJECT-TYPE
  SYNTAX INTEGER {
    static(1),
    dhcp(2),
    pppoe(3),
    pptp(4),
    modem(5),
    modemint(6),
    gsm(7)
  }
  ACCESS read-write
  STATUS mandatory
  DESCRIPTION
    "Variable name: ROUTER_MODE
    WebUi Label: Router mode
    Router mode: static,DHCP,PPPoE,PPTP,Modem,Modem Internal"
  ::= { mGuardNetwork 17 }


-- SECCLOUD_DIRECT_FACILITIES table
mGuardSecCloudDirectFacTable OBJECT-TYPE
  SYNTAX SEQUENCE OF MGuardSecCloudDirectFacEntry
  ACCESS not-accessible
  STATUS mandatory
  DESCRIPTION
    "A table of SECCLOUD_DIRECT_FACILITIES"
  ::= { mGuardSecCloud 5 }

-- SECCLOUD_DIRECT_FACILITIES table entry
mGuardSecCloudDirectFacEntry OBJECT-TYPE
  SYNTAX MGuardSecCloudDirectFacEntry
  ACCESS not-accessible
  STATUS mandatory
  DESCRIPTION
    "An entry of SECCLOUD_DIRECT_FACILITIES"
  INDEX { mGuardSecCloudDirectFacIndex }
  ::= { mGuardSecCloudDirectFacTable 1 }

MGuardSecCloudDirectFacEntry ::= SEQUENCE {
  mGuardSecCloudDirectFacIndex             INTEGER,
  mGuardSecCloudDirectFacID                DisplayString,
  mGuardSecCloudDirectFacComment           DisplayString,
  mGuardSecCloudDirectFacFWLogDefIn        INTEGER,
  mGuardSecCloudDirectFacFWLogDefOut       INTEGER,
  mGuardSecCloudDirectFacRowStatus         RowStatus
}

-- SECCLOUD_DIRECT_FACILITIES table index
mGuardSecCloudDirectFacIndex OBJECT-TYPE
  SYNTAX INTEGER (1..2147483647)
  ACCESS not-accessible
  STATUS mandatory
  DESCRIPTION
    "Index to SECCLOUD_DIRECT_FACILITIES"
  ::= { mGuardSecCloudDirectFacEntry 1 }

-- SECCLOUD_DIRECT_FACILITIES row status
mGuardSecCloudDirectFacRowStatus OBJECT-TYPE
  SYNTAX RowStatus
  ACCESS read-write
  STATUS mandatory
  DESCRIPTION
    "RowStatus of SECCLOUD_DIRECT_FACILITIES"
  ::= { mGuardSecCloudDirectFacEntry 6 }

-- SECCLOUD_DIRECT_FACILITIES.COMMENT
mGuardSecCloudDirectFacComment OBJECT-TYPE
  SYNTAX DisplayString
  ACCESS read-write
  STATUS mandatory
  DESCRIPTION
    "Variable name: SECCLOUD_DIRECT_FACILITIES.COMMENT
    WebUi Label: Comment
    Commentary or name for this entry."
  ::= { mGuardSecCloudDirectFacEntry 3 }


-- SECCLOUD_DIRECT_FACILITIES.ADDR table
mGuardSecCloudDirFacAddrTable OBJECT-TYPE
  SYNTAX SEQUENCE OF MGuardSecCloudDirFacAddrEntry
  ACCESS not-accessible
  STATUS mandatory
  DESCRIPTION
    "A table of SECCLOUD_DIRECT_FACILITIES.ADDR"
  ::= { mGuardSecCloudDirFac 1 }

-- SECCLOUD_DIRECT_FACILITIES.ADDR table entry
mGuardSecCloudDirFacAddrEntry OBJECT-TYPE
  SYNTAX MGuardSecCloudDirFacAddrEntry
  ACCESS not-accessible
  STATUS mandatory
  DESCRIPTION
    "An entry of SECCLOUD_DIRECT_FACILITIES.ADDR"
  INDEX { mGuardSecCloudDirectFacIndex, mGuardSecCloudDirFacAddrListIndex }
  ::= { mGuardSecCloudDirFacAddrTable 1 }

MGuardSecCloudDirFacAddrEntry ::= SEQUENCE {
  mGuardSecCloudDirFacAddrListIndex        INTEGER,
  mGuardSecCloudDirFacAddrCIDR             DisplayString,
  mGuardSecCloudDirFacAddrComment          DisplayString,
  mGuardSecCloudDirFacAddrRowStatus        RowStatus
}

-- SECCLOUD_DIRECT_FACILITIES.ADDR table index
mGuardSecCloudDirFacAddrListIndex OBJECT-TYPE
  SYNTAX INTEGER (1..2147483647)
  ACCESS not-accessible
  STATUS mandatory
  DESCRIPTION
    "Index to SECCLOUD_DIRECT_FACILITIES.ADDR"
  ::= { mGuardSecCloudDirFacAddrEntry 2 }

-- SECCLOUD_DIRECT_FACILITIES.ADDR row status
mGuardSecCloudDirFacAddrRowStatus OBJECT-TYPE
  SYNTAX RowStatus
  ACCESS read-write
  STATUS mandatory
  DESCRIPTION
    "RowStatus of SECCLOUD_DIRECT_FACILITIES.ADDR"
  ::= { mGuardSecCloudDirFacAddrEntry 5 }

-- SECCLOUD_DIRECT_FACILITIES.ADDR.COMMENT
mGuardSecCloudDirFacAddrComment OBJECT-TYPE
  SYNTAX DisplayString
  ACCESS read-write
  STATUS mandatory
  DESCRIPTION
    "Variable name: SECCLOUD_DIRECT_FACILITIES.ADDR.COMMENT
    WebUi Label: Comment
    Commentary or name for this entry."
  ::= { mGuardSecCloudDirFacAddrEntry 4 }

-- SECCLOUD_DIRECT_FACILITIES.ADDR.IP
mGuardSecCloudDirFacAddrCIDR OBJECT-TYPE
  SYNTAX DisplayString
  ACCESS read-write
  STATUS mandatory
  DESCRIPTION
    "Variable name: SECCLOUD_DIRECT_FACILITIES.ADDR.IP
    WebUi Label: IP
    The network address in CIDR notation."
  ::= { mGuardSecCloudDirFacAddrEntry 3 }


-- SECCLOUD_DIRECT_FACILITIES.FW_OUTGOING table
mGuardSecCloudDirFacFWOUTTable OBJECT-TYPE
  SYNTAX SEQUENCE OF MGuardSecCloudDirFacFWOUTEntry
  ACCESS not-accessible
  STATUS mandatory
  DESCRIPTION
    "A table of SECCLOUD_DIRECT_FACILITIES.FW_OUTGOING"
  ::= { mGuardSecCloudDirFac 3 }

-- SECCLOUD_DIRECT_FACILITIES.FW_OUTGOING table entry
mGuardSecCloudDirFacFWOUTEntry OBJECT-TYPE
  SYNTAX MGuardSecCloudDirFacFWOUTEntry
  ACCESS not-accessible
  STATUS mandatory
  DESCRIPTION
    "An entry of SECCLOUD_DIRECT_FACILITIES.FW_OUTGOING"
  INDEX { mGuardSecCloudDirectFacIndex, mGuardSecCloudDirFacFWOUTruleIndex }
  ::= { mGuardSecCloudDirFacFWOUTTable 1 }

MGuardSecCloudDirFacFWOUTEntry ::= SEQUENCE {
  mGuardSecCloudDirFacFWOUTruleIndex       INTEGER,
  mGuardSecCloudDirFacFWOUTfacilityIP      DisplayString,
  mGuardSecCloudDirFacFWOUTfacilityport    DisplayString,
  mGuardSecCloudDirFacFWOUTseatport        DisplayString,
  mGuardSecCloudDirFacFWOUTtarget          INTEGER,
  mGuardSecCloudDirFacFWOUTproto           INTEGER,
  mGuardSecCloudDirFacFWOUTlog             INTEGER,
  mGuardSecCloudDirFacFWOUTcomment         DisplayString,
  mGuardSecCloudDirFacFWOUTRowStatus       RowStatus
}

-- SECCLOUD_DIRECT_FACILITIES.FW_OUTGOING table index
mGuardSecCloudDirFacFWOUTruleIndex OBJECT-TYPE
  SYNTAX INTEGER (1..2147483647)
  ACCESS not-accessible
  STATUS mandatory
  DESCRIPTION
    "Index to SECCLOUD_DIRECT_FACILITIES.FW_OUTGOING"
  ::= { mGuardSecCloudDirFacFWOUTEntry 2 }

-- SECCLOUD_DIRECT_FACILITIES.FW_OUTGOING row status
mGuardSecCloudDirFacFWOUTRowStatus OBJECT-TYPE
  SYNTAX RowStatus
  ACCESS read-write
  STATUS mandatory
  DESCRIPTION
    "RowStatus of SECCLOUD_DIRECT_FACILITIES.FW_OUTGOING"
  ::= { mGuardSecCloudDirFacFWOUTEntry 10 }

-- SECCLOUD_DIRECT_FACILITIES.FW_OUTGOING.COMMENT
mGuardSecCloudDirFacFWOUTcomment OBJECT-TYPE
  SYNTAX DisplayString
  ACCESS read-write
  STATUS mandatory
  DESCRIPTION
    "Variable name: SECCLOUD_DIRECT_FACILITIES.FW_OUTGOING.COMMENT
    WebUi Label: Comment
    Commentary or name for this rule."
  ::= { mGuardSecCloudDirFacFWOUTEntry 9 }

-- SECCLOUD_DIRECT_FACILITIES.FW_OUTGOING.LOG
mGuardSecCloudDirFacFWOUTlog OBJECT-TYPE
  SYNTAX INTEGER {
    yes(1),
    no(2)
  }
  ACCESS read-write
  STATUS mandatory
  DESCRIPTION
    "Variable name: SECCLOUD_DIRECT_FACILITIES.FW_OUTGOING.LOG
    WebUi Label: Log
    Log packets matching this rule."
  ::= { mGuardSecCloudDirFacFWOUTEntry 8 }

-- SECCLOUD_DIRECT_FACILITIES.FW_OUTGOING.FACILITY_IP
mGuardSecCloudDirFacFWOUTfacilityIP OBJECT-TYPE
  SYNTAX DisplayString
  ACCESS read-write
  STATUS mandatory
  DESCRIPTION
    "Variable name: SECCLOUD_DIRECT_FACILITIES.FW_OUTGOING.FACILITY_IP
    WebUi Label: IP at facility
    The rule's facility IP address"
  ::= { mGuardSecCloudDirFacFWOUTEntry 3 }

-- SECCLOUD_DIRECT_FACILITIES.FW_OUTGOING.PROTO
mGuardSecCloudDirFacFWOUTproto OBJECT-TYPE
  SYNTAX INTEGER {
    tcp(1),
    udp(2),
    icmp(3),
    all(4),
    gre(5)
  }
  ACCESS read-write
  STATUS mandatory
  DESCRIPTION
    "Variable name: SECCLOUD_DIRECT_FACILITIES.FW_OUTGOING.PROTO
    WebUi Label: Protocol
    The rule's transport protocol"
  ::= { mGuardSecCloudDirFacFWOUTEntry 7 }

-- SECCLOUD_DIRECT_FACILITIES.FW_OUTGOING.FACILITY_PORT
mGuardSecCloudDirFacFWOUTfacilityport OBJECT-TYPE
  SYNTAX DisplayString
  ACCESS read-write
  STATUS mandatory
  DESCRIPTION
    "Variable name: SECCLOUD_DIRECT_FACILITIES.FW_OUTGOING.FACILITY_PORT
    WebUi Label: Port at facility
    The rule's facility port"
  ::= { mGuardSecCloudDirFacFWOUTEntry 4 }

-- SECCLOUD_DIRECT_FACILITIES.FW_OUTGOING.SEAT_PORT
mGuardSecCloudDirFacFWOUTseatport OBJECT-TYPE
  SYNTAX DisplayString
  ACCESS read-write
  STATUS mandatory
  DESCRIPTION
    "Variable name: SECCLOUD_DIRECT_FACILITIES.FW_OUTGOING.SEAT_PORT
    WebUi Label: Port at seat
    The rule's seat port"
  ::= { mGuardSecCloudDirFacFWOUTEntry 5 }

-- SECCLOUD_DIRECT_FACILITIES.FW_OUTGOING.TARGET
mGuardSecCloudDirFacFWOUTtarget OBJECT-TYPE
  SYNTAX INTEGER {
    accept(1),
    reject(2),
    drop(3)
  }
  ACCESS read-write
  STATUS mandatory
  DESCRIPTION
    "Variable name: SECCLOUD_DIRECT_FACILITIES.FW_OUTGOING.TARGET
    WebUi Label: Action
    The target of the rule (accept/reject/drop)."
  ::= { mGuardSecCloudDirFacFWOUTEntry 6 }

-- SECCLOUD_DIRECT_FACILITIES.LOG_DEFAULT_OUTGOING
mGuardSecCloudDirectFacFWLogDefOut OBJECT-TYPE
  SYNTAX INTEGER {
    yes(1),
    no(2)
  }
  ACCESS read-write
  STATUS mandatory
  DESCRIPTION
    "Variable name: SECCLOUD_DIRECT_FACILITIES.LOG_DEFAULT_OUTGOING
    WebUi Label: Log entries for unknown connection attempts
    Log entries for undefined outgoing connection attempts?"
  ::= { mGuardSecCloudDirectFacEntry 5 }


-- SECCLOUD_DIRECT_FACILITIES.FW_INCOMING table
mGuardSecCloudDirFacFWINTable OBJECT-TYPE
  SYNTAX SEQUENCE OF MGuardSecCloudDirFacFWINEntry
  ACCESS not-accessible
  STATUS mandatory
  DESCRIPTION
    "A table of SECCLOUD_DIRECT_FACILITIES.FW_INCOMING"
  ::= { mGuardSecCloudDirFac 2 }

-- SECCLOUD_DIRECT_FACILITIES.FW_INCOMING table entry
mGuardSecCloudDirFacFWINEntry OBJECT-TYPE
  SYNTAX MGuardSecCloudDirFacFWINEntry
  ACCESS not-accessible
  STATUS mandatory
  DESCRIPTION
    "An entry of SECCLOUD_DIRECT_FACILITIES.FW_INCOMING"
  INDEX { mGuardSecCloudDirectFacIndex, mGuardSecCloudDirFacFWINruleIndex }
  ::= { mGuardSecCloudDirFacFWINTable 1 }

MGuardSecCloudDirFacFWINEntry ::= SEQUENCE {
  mGuardSecCloudDirFacFWINruleIndex        INTEGER,
  mGuardSecCloudDirFacFWINfacilityIP       DisplayString,
  mGuardSecCloudDirFacFWINfacilityport     DisplayString,
  mGuardSecCloudDirFacFWINseatport         DisplayString,
  mGuardSecCloudDirFacFWINtarget           INTEGER,
  mGuardSecCloudDirFacFWINproto            INTEGER,
  mGuardSecCloudDirFacFWINlog              INTEGER,
  mGuardSecCloudDirFacFWINcomment          DisplayString,
  mGuardSecCloudDirFacFWINRowStatus        RowStatus
}

-- SECCLOUD_DIRECT_FACILITIES.FW_INCOMING table index
mGuardSecCloudDirFacFWINruleIndex OBJECT-TYPE
  SYNTAX INTEGER (1..2147483647)
  ACCESS not-accessible
  STATUS mandatory
  DESCRIPTION
    "Index to SECCLOUD_DIRECT_FACILITIES.FW_INCOMING"
  ::= { mGuardSecCloudDirFacFWINEntry 2 }

-- SECCLOUD_DIRECT_FACILITIES.FW_INCOMING row status
mGuardSecCloudDirFacFWINRowStatus OBJECT-TYPE
  SYNTAX RowStatus
  ACCESS read-write
  STATUS mandatory
  DESCRIPTION
    "RowStatus of SECCLOUD_DIRECT_FACILITIES.FW_INCOMING"
  ::= { mGuardSecCloudDirFacFWINEntry 10 }

-- SECCLOUD_DIRECT_FACILITIES.FW_INCOMING.COMMENT
mGuardSecCloudDirFacFWINcomment OBJECT-TYPE
  SYNTAX DisplayString
  ACCESS read-write
  STATUS mandatory
  DESCRIPTION
    "Variable name: SECCLOUD_DIRECT_FACILITIES.FW_INCOMING.COMMENT
    WebUi Label: Comment
    Commentary or name for this rule."
  ::= { mGuardSecCloudDirFacFWINEntry 9 }

-- SECCLOUD_DIRECT_FACILITIES.FW_INCOMING.LOG
mGuardSecCloudDirFacFWINlog OBJECT-TYPE
  SYNTAX INTEGER {
    yes(1),
    no(2)
  }
  ACCESS read-write
  STATUS mandatory
  DESCRIPTION
    "Variable name: SECCLOUD_DIRECT_FACILITIES.FW_INCOMING.LOG
    WebUi Label: Log
    Log packets matching this rule."
  ::= { mGuardSecCloudDirFacFWINEntry 8 }

-- SECCLOUD_DIRECT_FACILITIES.FW_INCOMING.FACILITY_IP
mGuardSecCloudDirFacFWINfacilityIP OBJECT-TYPE
  SYNTAX DisplayString
  ACCESS read-write
  STATUS mandatory
  DESCRIPTION
    "Variable name: SECCLOUD_DIRECT_FACILITIES.FW_INCOMING.FACILITY_IP
    WebUi Label: IP at facility
    The rule's facility IP address"
  ::= { mGuardSecCloudDirFacFWINEntry 3 }

-- SECCLOUD_DIRECT_FACILITIES.FW_INCOMING.PROTO
mGuardSecCloudDirFacFWINproto OBJECT-TYPE
  SYNTAX INTEGER {
    tcp(1),
    udp(2),
    icmp(3),
    all(4),
    gre(5)
  }
  ACCESS read-write
  STATUS mandatory
  DESCRIPTION
    "Variable name: SECCLOUD_DIRECT_FACILITIES.FW_INCOMING.PROTO
    WebUi Label: Protocol
    The rule's transport protocol"
  ::= { mGuardSecCloudDirFacFWINEntry 7 }

-- SECCLOUD_DIRECT_FACILITIES.FW_INCOMING.FACILITY_PORT
mGuardSecCloudDirFacFWINfacilityport OBJECT-TYPE
  SYNTAX DisplayString
  ACCESS read-write
  STATUS mandatory
  DESCRIPTION
    "Variable name: SECCLOUD_DIRECT_FACILITIES.FW_INCOMING.FACILITY_PORT
    WebUi Label: Port at facility
    The rule's facility port"
  ::= { mGuardSecCloudDirFacFWINEntry 4 }

-- SECCLOUD_DIRECT_FACILITIES.FW_INCOMING.SEAT_PORT
mGuardSecCloudDirFacFWINseatport OBJECT-TYPE
  SYNTAX DisplayString
  ACCESS read-write
  STATUS mandatory
  DESCRIPTION
    "Variable name: SECCLOUD_DIRECT_FACILITIES.FW_INCOMING.SEAT_PORT
    WebUi Label: Port at seat
    The rule's seat port"
  ::= { mGuardSecCloudDirFacFWINEntry 5 }

-- SECCLOUD_DIRECT_FACILITIES.FW_INCOMING.TARGET
mGuardSecCloudDirFacFWINtarget OBJECT-TYPE
  SYNTAX INTEGER {
    accept(1),
    reject(2),
    drop(3)
  }
  ACCESS read-write
  STATUS mandatory
  DESCRIPTION
    "Variable name: SECCLOUD_DIRECT_FACILITIES.FW_INCOMING.TARGET
    WebUi Label: Action
    The target of the rule (accept/reject/drop)."
  ::= { mGuardSecCloudDirFacFWINEntry 6 }

-- SECCLOUD_DIRECT_FACILITIES.ID
mGuardSecCloudDirectFacID OBJECT-TYPE
  SYNTAX DisplayString
  ACCESS read-write
  STATUS mandatory
  DESCRIPTION
    "Variable name: SECCLOUD_DIRECT_FACILITIES.ID
    WebUi Label: ID
    ID of the seat."
  ::= { mGuardSecCloudDirectFacEntry 2 }

-- SECCLOUD_DIRECT_FACILITIES.LOG_DEFAULT_INCOMING
mGuardSecCloudDirectFacFWLogDefIn OBJECT-TYPE
  SYNTAX INTEGER {
    yes(1),
    no(2)
  }
  ACCESS read-write
  STATUS mandatory
  DESCRIPTION
    "Variable name: SECCLOUD_DIRECT_FACILITIES.LOG_DEFAULT_INCOMING
    WebUi Label: Log entries for unknown connection attempts
    Log entries for undefined incoming connection attempts?"
  ::= { mGuardSecCloudDirectFacEntry 4 }


-- SECCLOUD_DIRECT_SERVICE_SEATS table
mGuardSecCloudDirectSeatTable OBJECT-TYPE
  SYNTAX SEQUENCE OF MGuardSecCloudDirectSeatEntry
  ACCESS not-accessible
  STATUS mandatory
  DESCRIPTION
    "A table of SECCLOUD_DIRECT_SERVICE_SEATS"
  ::= { mGuardSecCloud 4 }

-- SECCLOUD_DIRECT_SERVICE_SEATS table entry
mGuardSecCloudDirectSeatEntry OBJECT-TYPE
  SYNTAX MGuardSecCloudDirectSeatEntry
  ACCESS not-accessible
  STATUS mandatory
  DESCRIPTION
    "An entry of SECCLOUD_DIRECT_SERVICE_SEATS"
  INDEX { mGuardSecCloudDirectSeatIndex }
  ::= { mGuardSecCloudDirectSeatTable 1 }

MGuardSecCloudDirectSeatEntry ::= SEQUENCE {
  mGuardSecCloudDirectSeatIndex            INTEGER,
  mGuardSecCloudDirectSeatID               DisplayString,
  mGuardSecCloudDirectSeatIP               IpAddress,
  mGuardSecCloudDirectSeatComment          DisplayString,
  mGuardSecCloudDirectSeatRowStatus        RowStatus
}

-- SECCLOUD_DIRECT_SERVICE_SEATS table index
mGuardSecCloudDirectSeatIndex OBJECT-TYPE
  SYNTAX INTEGER (1..2147483647)
  ACCESS not-accessible
  STATUS mandatory
  DESCRIPTION
    "Index to SECCLOUD_DIRECT_SERVICE_SEATS"
  ::= { mGuardSecCloudDirectSeatEntry 1 }

-- SECCLOUD_DIRECT_SERVICE_SEATS row status
mGuardSecCloudDirectSeatRowStatus OBJECT-TYPE
  SYNTAX RowStatus
  ACCESS read-write
  STATUS mandatory
  DESCRIPTION
    "RowStatus of SECCLOUD_DIRECT_SERVICE_SEATS"
  ::= { mGuardSecCloudDirectSeatEntry 5 }

-- SECCLOUD_DIRECT_SERVICE_SEATS.COMMENT
mGuardSecCloudDirectSeatComment OBJECT-TYPE
  SYNTAX DisplayString
  ACCESS read-write
  STATUS mandatory
  DESCRIPTION
    "Variable name: SECCLOUD_DIRECT_SERVICE_SEATS.COMMENT
    WebUi Label: Comment
    Commentary or name for this entry."
  ::= { mGuardSecCloudDirectSeatEntry 4 }

-- SECCLOUD_DIRECT_SERVICE_SEATS.IP
mGuardSecCloudDirectSeatIP OBJECT-TYPE
  SYNTAX IpAddress
  ACCESS read-write
  STATUS mandatory
  DESCRIPTION
    "Variable name: SECCLOUD_DIRECT_SERVICE_SEATS.IP
    WebUi Label: IP
    IP address of the seat."
  ::= { mGuardSecCloudDirectSeatEntry 3 }

-- SECCLOUD_DIRECT_SERVICE_SEATS.ID
mGuardSecCloudDirectSeatID OBJECT-TYPE
  SYNTAX DisplayString
  ACCESS read-write
  STATUS mandatory
  DESCRIPTION
    "Variable name: SECCLOUD_DIRECT_SERVICE_SEATS.ID
    WebUi Label: ID
    ID of the seat."
  ::= { mGuardSecCloudDirectSeatEntry 2 }

-- SECCLOUD_ENGINE_ENABLE
mGuardSecCloudEngineEnable OBJECT-TYPE
  SYNTAX INTEGER {
    yes(1),
    no(2)
  }
  ACCESS read-write
  STATUS mandatory
  DESCRIPTION
    "Variable name: SECCLOUD_ENGINE_ENABLE
    WebUi Label: Enable the engine
    Enable Secure Cloud Routing Engine"
  ::= { mGuardSecCloudEngine 1 }

-- SECCLOUD_MGUARD_IP
mGuardSecCloudEngineRequestIP OBJECT-TYPE
  SYNTAX IpAddress
  ACCESS read-write
  STATUS mandatory
  DESCRIPTION
    "Variable name: SECCLOUD_MGUARD_IP
    WebUi Label: mGuard IP internally used to access the portal HTTPS server
    IP used as source for access to the portal WEB-GUI"
  ::= { mGuardSecCloudEngine 3 }


-- SECCLOUD_PORTAL_ACCESS table
mGuardSecCloudPortalAccessTable OBJECT-TYPE
  SYNTAX SEQUENCE OF MGuardSecCloudPortalAccessEntry
  ACCESS not-accessible
  STATUS mandatory
  DESCRIPTION
    "A table of SECCLOUD_PORTAL_ACCESS"
  ::= { mGuardSecCloud 2 }

-- SECCLOUD_PORTAL_ACCESS table entry
mGuardSecCloudPortalAccessEntry OBJECT-TYPE
  SYNTAX MGuardSecCloudPortalAccessEntry
  ACCESS not-accessible
  STATUS mandatory
  DESCRIPTION
    "An entry of SECCLOUD_PORTAL_ACCESS"
  INDEX { mGuardSecCloudPortalAccessIndex }
  ::= { mGuardSecCloudPortalAccessTable 1 }

MGuardSecCloudPortalAccessEntry ::= SEQUENCE {
  mGuardSecCloudPortalAccessIndex          INTEGER,
  mGuardSecCloudPortalAccessInPort         DisplayString,
  mGuardSecCloudPortalAccessToPort         DisplayString,
  mGuardSecCloudPortalAccessComment        DisplayString,
  mGuardSecCloudPortalAccessRowStatus      RowStatus
}

-- SECCLOUD_PORTAL_ACCESS table index
mGuardSecCloudPortalAccessIndex OBJECT-TYPE
  SYNTAX INTEGER (1..2147483647)
  ACCESS not-accessible
  STATUS mandatory
  DESCRIPTION
    "Index to SECCLOUD_PORTAL_ACCESS"
  ::= { mGuardSecCloudPortalAccessEntry 1 }

-- SECCLOUD_PORTAL_ACCESS row status
mGuardSecCloudPortalAccessRowStatus OBJECT-TYPE
  SYNTAX RowStatus
  ACCESS read-write
  STATUS mandatory
  DESCRIPTION
    "RowStatus of SECCLOUD_PORTAL_ACCESS"
  ::= { mGuardSecCloudPortalAccessEntry 5 }

-- SECCLOUD_PORTAL_ACCESS.COMMENT
mGuardSecCloudPortalAccessComment OBJECT-TYPE
  SYNTAX DisplayString
  ACCESS read-write
  STATUS mandatory
  DESCRIPTION
    "Variable name: SECCLOUD_PORTAL_ACCESS.COMMENT
    WebUi Label: Comment
    Commentary or name for this rule."
  ::= { mGuardSecCloudPortalAccessEntry 4 }

-- SECCLOUD_PORTAL_ACCESS.OUT_PORT
mGuardSecCloudPortalAccessToPort OBJECT-TYPE
  SYNTAX DisplayString
  ACCESS read-write
  STATUS mandatory
  DESCRIPTION
    "Variable name: SECCLOUD_PORTAL_ACCESS.OUT_PORT
    WebUi Label: Internally used port
    Port to which to forward to, service names allowed."
  ::= { mGuardSecCloudPortalAccessEntry 3 }

-- SECCLOUD_PORTAL_ACCESS.IN_PORT
mGuardSecCloudPortalAccessInPort OBJECT-TYPE
  SYNTAX DisplayString
  ACCESS read-write
  STATUS mandatory
  DESCRIPTION
    "Variable name: SECCLOUD_PORTAL_ACCESS.IN_PORT
    WebUi Label: Externally contacted port
    Port on which to listen, service names allowed."
  ::= { mGuardSecCloudPortalAccessEntry 2 }

-- SECCLOUD_PORTAL_IP
mGuardSecCloudEnginePortalIP OBJECT-TYPE
  SYNTAX IpAddress
  ACCESS read-write
  STATUS mandatory
  DESCRIPTION
    "Variable name: SECCLOUD_PORTAL_IP
    WebUi Label: Internally used IP of portal HTTPS server
    IP of the portal WEB-GUI"
  ::= { mGuardSecCloudEngine 2 }


-- SECCLOUD_SERVICE_SEAT_POOLS table
mGuardSecCloudSeatPoolTable OBJECT-TYPE
  SYNTAX SEQUENCE OF MGuardSecCloudSeatPoolEntry
  ACCESS not-accessible
  STATUS mandatory
  DESCRIPTION
    "A table of SECCLOUD_SERVICE_SEAT_POOLS"
  ::= { mGuardSecCloud 3 }

-- SECCLOUD_SERVICE_SEAT_POOLS table entry
mGuardSecCloudSeatPoolEntry OBJECT-TYPE
  SYNTAX MGuardSecCloudSeatPoolEntry
  ACCESS not-accessible
  STATUS mandatory
  DESCRIPTION
    "An entry of SECCLOUD_SERVICE_SEAT_POOLS"
  INDEX { mGuardSecCloudSeatPoolIndex }
  ::= { mGuardSecCloudSeatPoolTable 1 }

MGuardSecCloudSeatPoolEntry ::= SEQUENCE {
  mGuardSecCloudSeatPoolIndex              INTEGER,
  mGuardSecCloudSeatPoolCIDR               DisplayString,
  mGuardSecCloudSeatPoolComment            DisplayString,
  mGuardSecCloudSeatPoolRowStatus          RowStatus
}

-- SECCLOUD_SERVICE_SEAT_POOLS table index
mGuardSecCloudSeatPoolIndex OBJECT-TYPE
  SYNTAX INTEGER (1..2147483647)
  ACCESS not-accessible
  STATUS mandatory
  DESCRIPTION
    "Index to SECCLOUD_SERVICE_SEAT_POOLS"
  ::= { mGuardSecCloudSeatPoolEntry 1 }

-- SECCLOUD_SERVICE_SEAT_POOLS row status
mGuardSecCloudSeatPoolRowStatus OBJECT-TYPE
  SYNTAX RowStatus
  ACCESS read-write
  STATUS mandatory
  DESCRIPTION
    "RowStatus of SECCLOUD_SERVICE_SEAT_POOLS"
  ::= { mGuardSecCloudSeatPoolEntry 4 }

-- SECCLOUD_SERVICE_SEAT_POOLS.COMMENT
mGuardSecCloudSeatPoolComment OBJECT-TYPE
  SYNTAX DisplayString
  ACCESS read-write
  STATUS mandatory
  DESCRIPTION
    "Variable name: SECCLOUD_SERVICE_SEAT_POOLS.COMMENT
    WebUi Label: Comment
    Commentary or name for this entry."
  ::= { mGuardSecCloudSeatPoolEntry 3 }

-- SECCLOUD_SERVICE_SEAT_POOLS.IP
mGuardSecCloudSeatPoolCIDR OBJECT-TYPE
  SYNTAX DisplayString
  ACCESS read-write
  STATUS mandatory
  DESCRIPTION
    "Variable name: SECCLOUD_SERVICE_SEAT_POOLS.IP
    WebUi Label: Pool (CIDR)
    CIDR notation of pool."
  ::= { mGuardSecCloudSeatPoolEntry 2 }

-- SECCLOUD_SERVICE_URI
mGuardSecCloudEngineServiceURI OBJECT-TYPE
  SYNTAX DisplayString
  ACCESS read-write
  STATUS mandatory
  DESCRIPTION
    "Variable name: SECCLOUD_SERVICE_URI
    WebUi Label: Internally used URI of portal configuration service
    URI of the portal service provider"
  ::= { mGuardSecCloudEngine 4 }

-- SECSTICK_CLIENT_ALIVE_COUNT_MAX
mGuardSECStickClientAliveMaxC OBJECT-TYPE
  SYNTAX INTEGER(1..10)
  ACCESS read-write
  STATUS mandatory
  DESCRIPTION
    "Variable name: SECSTICK_CLIENT_ALIVE_COUNT_MAX
    WebUi Label: Maximum number of missing signs of life
    Sets the number of client alive messages (see
    mGuardSECStickClientAliveSecs) which may be sent without the SEC-Stick
    server receiving any messages back from the client. If this threshold
    is reached while client alive messages are being sent, the mGuard will
    disconnect the client, terminating the session."
  ::= { mGuardSECStick 10 }

-- SECSTICK_CLIENT_ALIVE_INTERVAL_SECS
mGuardSECStickClientAliveSecs OBJECT-TYPE
  SYNTAX INTEGER(0..3600)
  ACCESS read-write
  STATUS mandatory
  DESCRIPTION
    "Variable name: SECSTICK_CLIENT_ALIVE_INTERVAL_SECS
    WebUi Label: Delay between requests for a sign of life (The value 0 indicates that
     these messages will not be sent.)
    Sets a timeout interval in seconds after which if no data has been
    received from the client, the SEC-Stick server will send a message
    through the encrypted channel to request a response from the client.
    The default is 0, indicating that these messages will not be sent to
    the client. This object (having a default value of 120s) replaces the
    now deprecated mGuardSECStickClientAliveSeconds object which had the
    default 0."
  ::= { mGuardSECStick 14 }


-- SECSTICK_CONNECTION table
mGuardSECStickConnectionTable OBJECT-TYPE
  SYNTAX SEQUENCE OF MGuardSECStickConnectionEntry
  ACCESS not-accessible
  STATUS mandatory
  DESCRIPTION
    "A table of SECSTICK_CONNECTION"
  ::= { mGuardSECStick 6 }

-- SECSTICK_CONNECTION table entry
mGuardSECStickConnectionEntry OBJECT-TYPE
  SYNTAX MGuardSECStickConnectionEntry
  ACCESS not-accessible
  STATUS mandatory
  DESCRIPTION
    "An entry of SECSTICK_CONNECTION"
  INDEX { mGuardSECStickConIndex }
  ::= { mGuardSECStickConnectionTable 1 }

MGuardSECStickConnectionEntry ::= SEQUENCE {
  mGuardSECStickConIndex                   INTEGER,
  mGuardSECStickConEnable                  INTEGER,
  mGuardSECStickConName                    DisplayString,
  mGuardSECStickConCompany                 DisplayString,
  mGuardSECStickConUserName                DisplayString,
  mGuardSECStickConPubKey                  DisplayString,
  mGuardSECStickConRowStatus               RowStatus,
  mGuardSECStickConComment                 DisplayString,
  mGuardSECStickConContact                 DisplayString
}

-- SECSTICK_CONNECTION table index
mGuardSECStickConIndex OBJECT-TYPE
  SYNTAX INTEGER (1..2147483647)
  ACCESS not-accessible
  STATUS mandatory
  DESCRIPTION
    "Index to SECSTICK_CONNECTION"
  ::= { mGuardSECStickConnectionEntry 1 }

-- SECSTICK_CONNECTION row status
mGuardSECStickConRowStatus OBJECT-TYPE
  SYNTAX RowStatus
  ACCESS read-write
  STATUS mandatory
  DESCRIPTION
    "RowStatus of SECSTICK_CONNECTION"
  ::= { mGuardSECStickConnectionEntry 7 }

-- SECSTICK_CONNECTION.COMMENT
mGuardSECStickConComment OBJECT-TYPE
  SYNTAX DisplayString
  ACCESS read-write
  STATUS mandatory
  DESCRIPTION
    "Variable name: SECSTICK_CONNECTION.COMMENT
    WebUi Label: Comment
    Comment describing the purpose of the SEC-Stick connection."
  ::= { mGuardSECStickConnectionEntry 8 }


-- SECSTICK_CONNECTION.REMOTE table
mGuardSECStickRemTable OBJECT-TYPE
  SYNTAX SEQUENCE OF MGuardSECStickRemEntry
  ACCESS not-accessible
  STATUS mandatory
  DESCRIPTION
    "A table of SECSTICK_CONNECTION.REMOTE"
  ::= { mGuardSECStickRemote 1 }

-- SECSTICK_CONNECTION.REMOTE table entry
mGuardSECStickRemEntry OBJECT-TYPE
  SYNTAX MGuardSECStickRemEntry
  ACCESS not-accessible
  STATUS mandatory
  DESCRIPTION
    "An entry of SECSTICK_CONNECTION.REMOTE"
  INDEX { mGuardSECStickConIndex, mGuardSECStickRemRuleIndex }
  ::= { mGuardSECStickRemTable 1 }

MGuardSECStickRemEntry ::= SEQUENCE {
  mGuardSECStickRemRuleIndex               INTEGER,
  mGuardSECStickRemRowStatus               RowStatus,
  mGuardSECStickRemPort                    INTEGER
}

-- SECSTICK_CONNECTION.REMOTE table index
mGuardSECStickRemRuleIndex OBJECT-TYPE
  SYNTAX INTEGER (1..2147483647)
  ACCESS not-accessible
  STATUS mandatory
  DESCRIPTION
    "Index to SECSTICK_CONNECTION.REMOTE"
  ::= { mGuardSECStickRemEntry 2 }

-- SECSTICK_CONNECTION.REMOTE row status
mGuardSECStickRemRowStatus OBJECT-TYPE
  SYNTAX RowStatus
  ACCESS read-write
  STATUS mandatory
  DESCRIPTION
    "RowStatus of SECSTICK_CONNECTION.REMOTE"
  ::= { mGuardSECStickRemEntry 4 }

-- SECSTICK_CONNECTION.REMOTE.PORT
mGuardSECStickRemPort OBJECT-TYPE
  SYNTAX INTEGER(1024..65535)
  ACCESS read-write
  STATUS mandatory
  DESCRIPTION
    "Variable name: SECSTICK_CONNECTION.REMOTE.PORT
    WebUi Label: Port
    The port to connect to (number or service name)."
  ::= { mGuardSECStickRemEntry 5 }

-- SECSTICK_CONNECTION.SSH_USERNAME
mGuardSECStickConUserName OBJECT-TYPE
  SYNTAX DisplayString
  ACCESS read-write
  STATUS mandatory
  DESCRIPTION
    "Variable name: SECSTICK_CONNECTION.SSH_USERNAME
    WebUi Label: User name
    SSH user name for the connection."
  ::= { mGuardSECStickConnectionEntry 5 }


-- SECSTICK_CONNECTION.DESTINATION table
mGuardSECStickTunTable OBJECT-TYPE
  SYNTAX SEQUENCE OF MGuardSECStickTunEntry
  ACCESS not-accessible
  STATUS mandatory
  DESCRIPTION
    "A table of SECSTICK_CONNECTION.DESTINATION"
  ::= { mGuardSECStickTunnel 1 }

-- SECSTICK_CONNECTION.DESTINATION table entry
mGuardSECStickTunEntry OBJECT-TYPE
  SYNTAX MGuardSECStickTunEntry
  ACCESS not-accessible
  STATUS mandatory
  DESCRIPTION
    "An entry of SECSTICK_CONNECTION.DESTINATION"
  INDEX { mGuardSECStickConIndex, mGuardSECStickTunRuleIndex }
  ::= { mGuardSECStickTunTable 1 }

MGuardSECStickTunEntry ::= SEQUENCE {
  mGuardSECStickTunRuleIndex               INTEGER,
  mGuardSECStickTunDestIP                  IpAddress,
  mGuardSECStickTunRowStatus               RowStatus,
  mGuardSECStickTunDestPort                INTEGER
}

-- SECSTICK_CONNECTION.DESTINATION table index
mGuardSECStickTunRuleIndex OBJECT-TYPE
  SYNTAX INTEGER (1..2147483647)
  ACCESS not-accessible
  STATUS mandatory
  DESCRIPTION
    "Index to SECSTICK_CONNECTION.DESTINATION"
  ::= { mGuardSECStickTunEntry 2 }

-- SECSTICK_CONNECTION.DESTINATION row status
mGuardSECStickTunRowStatus OBJECT-TYPE
  SYNTAX RowStatus
  ACCESS read-write
  STATUS mandatory
  DESCRIPTION
    "RowStatus of SECSTICK_CONNECTION.DESTINATION"
  ::= { mGuardSECStickTunEntry 5 }

-- SECSTICK_CONNECTION.DESTINATION.IP
mGuardSECStickTunDestIP OBJECT-TYPE
  SYNTAX IpAddress
  ACCESS read-write
  STATUS mandatory
  DESCRIPTION
    "Variable name: SECSTICK_CONNECTION.DESTINATION.IP
    WebUi Label: IP
    The IP address to connect to."
  ::= { mGuardSECStickTunEntry 3 }

-- SECSTICK_CONNECTION.DESTINATION.PORT
mGuardSECStickTunDestPort OBJECT-TYPE
  SYNTAX INTEGER(1..65535)
  ACCESS read-write
  STATUS mandatory
  DESCRIPTION
    "Variable name: SECSTICK_CONNECTION.DESTINATION.PORT
    WebUi Label: Port
    The port to connect to (number or service name)."
  ::= { mGuardSECStickTunEntry 6 }

-- SECSTICK_CONNECTION.SSH_KEY
mGuardSECStickConPubKey OBJECT-TYPE
  SYNTAX DisplayString
  ACCESS read-write
  STATUS mandatory
  DESCRIPTION
    "Variable name: SECSTICK_CONNECTION.SSH_KEY
    WebUi Label: SSH public key (including ssh-dss or ssh-rsa)
    SSH public key used to authenticate user for the connection."
  ::= { mGuardSECStickConnectionEntry 6 }

-- SECSTICK_CONNECTION.STICK_ENABLED
mGuardSECStickConEnable OBJECT-TYPE
  SYNTAX INTEGER {
    yes(1),
    no(2)
  }
  ACCESS read-write
  STATUS mandatory
  DESCRIPTION
    "Variable name: SECSTICK_CONNECTION.STICK_ENABLED
    WebUi Label: Enabled
    Is the connection enabled: yes / no ."
  ::= { mGuardSECStickConnectionEntry 2 }

-- SECSTICK_CONNECTION.SSH_COMPANY
mGuardSECStickConCompany OBJECT-TYPE
  SYNTAX DisplayString
  ACCESS read-write
  STATUS mandatory
  DESCRIPTION
    "Variable name: SECSTICK_CONNECTION.SSH_COMPANY
    WebUi Label: Company
    Informational company name for the connection."
  ::= { mGuardSECStickConnectionEntry 4 }

-- SECSTICK_CONNECTION.CONTACT
mGuardSECStickConContact OBJECT-TYPE
  SYNTAX DisplayString
  ACCESS read-write
  STATUS mandatory
  DESCRIPTION
    "Variable name: SECSTICK_CONNECTION.CONTACT
    WebUi Label: Contact
    Contact information."
  ::= { mGuardSECStickConnectionEntry 9 }

-- SECSTICK_CONNECTION.SSH_NAME
mGuardSECStickConName OBJECT-TYPE
  SYNTAX DisplayString
  ACCESS read-write
  STATUS mandatory
  DESCRIPTION
    "Variable name: SECSTICK_CONNECTION.SSH_NAME
    WebUi Label: A descriptive name of the user
    Informational name for the connection."
  ::= { mGuardSECStickConnectionEntry 3 }

-- SECSTICK_ENABLE
mGuardSECStickEnable OBJECT-TYPE
  SYNTAX INTEGER {
    yes(1),
    no(2)
  }
  ACCESS read-write
  STATUS mandatory
  DESCRIPTION
    "Variable name: SECSTICK_ENABLE
    WebUi Label: Enable SEC-Stick service
    Enable SEC-Stick support."
  ::= { mGuardSECStick 1 }

-- SECSTICK_LOGIN_ALLOWED_MAX
mGuardSECSStickLoginMax OBJECT-TYPE
  SYNTAX INTEGER
  ACCESS read-write
  STATUS mandatory
  DESCRIPTION
    "Variable name: SECSTICK_LOGIN_ALLOWED_MAX
    WebUi Label: Maximum number of cumulative concurrent sessions for all users
    Sets the maximum number of allowed concurrent authenticated and active
    SEC-Stick sessions. The SSH daemon may allow additional not yet
    authenticated sessions."
  ::= { mGuardSECStick 12 }

-- SECSTICK_PER_USER_LOGIN_ALLOWED_MAX
mGuardSECStickPerUserLoginMax OBJECT-TYPE
  SYNTAX INTEGER
  ACCESS read-write
  STATUS mandatory
  DESCRIPTION
    "Variable name: SECSTICK_PER_USER_LOGIN_ALLOWED_MAX
    WebUi Label: Maximum number of concurrent sessions for one user
    Sets the maximum number of allowed concurrent authenticated and active
    SSH sessions of a single user."
  ::= { mGuardSECStick 13 }

-- SECSTICK_REMOTE_ACCESS_RULES
mGuardSECStickRemoteUUID OBJECT-TYPE
  SYNTAX DisplayString
  ACCESS read-only
  STATUS mandatory
  DESCRIPTION
    "Variable name: SECSTICK_REMOTE_ACCESS_RULES
    WebUi Label: Allowed networks
    Universally Unique Identifier (UUID, RFC 4122) used for
    mGuardSECStickRemoteFWRuleTable logging."
  ::= { mGuardSECStick 4 }


-- SECSTICK_REMOTE_ACCESS_RULES table
mGuardSECStickRemoteFWRuleTable OBJECT-TYPE
  SYNTAX SEQUENCE OF MGuardSECStickRemoteFWRuleEntry
  ACCESS not-accessible
  STATUS mandatory
  DESCRIPTION
    "A table of SECSTICK_REMOTE_ACCESS_RULES"
  ::= { mGuardSECStick 5 }

-- SECSTICK_REMOTE_ACCESS_RULES table entry
mGuardSECStickRemoteFWRuleEntry OBJECT-TYPE
  SYNTAX MGuardSECStickRemoteFWRuleEntry
  ACCESS not-accessible
  STATUS mandatory
  DESCRIPTION
    "An entry of SECSTICK_REMOTE_ACCESS_RULES"
  INDEX { mGuardSECStickFWruleIndex }
  ::= { mGuardSECStickRemoteFWRuleTable 1 }

MGuardSECStickRemoteFWRuleEntry ::= SEQUENCE {
  mGuardSECStickFWruleIndex                INTEGER,
  mGuardSECStickFWsourceIP                 DisplayString,
  mGuardSECStickFWinterface                INTEGER,
  mGuardSECStickFWtarget                   INTEGER,
  mGuardSECStickFWlog                      INTEGER,
  mGuardSECStickFWRowStatus                RowStatus,
  mGuardSECStickFWcomment                  DisplayString,
  mGuardSECStickFWfromMAC                  MacAddress
}

-- SECSTICK_REMOTE_ACCESS_RULES table index
mGuardSECStickFWruleIndex OBJECT-TYPE
  SYNTAX INTEGER (1..2147483647)
  ACCESS not-accessible
  STATUS mandatory
  DESCRIPTION
    "Index to SECSTICK_REMOTE_ACCESS_RULES"
  ::= { mGuardSECStickRemoteFWRuleEntry 1 }

-- SECSTICK_REMOTE_ACCESS_RULES row status
mGuardSECStickFWRowStatus OBJECT-TYPE
  SYNTAX RowStatus
  ACCESS read-write
  STATUS mandatory
  DESCRIPTION
    "RowStatus of SECSTICK_REMOTE_ACCESS_RULES"
  ::= { mGuardSECStickRemoteFWRuleEntry 6 }

-- SECSTICK_REMOTE_ACCESS_RULES.COMMENT
mGuardSECStickFWcomment OBJECT-TYPE
  SYNTAX DisplayString
  ACCESS read-write
  STATUS mandatory
  DESCRIPTION
    "Variable name: SECSTICK_REMOTE_ACCESS_RULES.COMMENT
    WebUi Label: Comment
    Commentary or name for this rule."
  ::= { mGuardSECStickRemoteFWRuleEntry 7 }

-- SECSTICK_REMOTE_ACCESS_RULES.LOG
mGuardSECStickFWlog OBJECT-TYPE
  SYNTAX INTEGER {
    yes(1),
    no(2)
  }
  ACCESS read-write
  STATUS mandatory
  DESCRIPTION
    "Variable name: SECSTICK_REMOTE_ACCESS_RULES.LOG
    WebUi Label: Log
    Log packets matching this rule ?"
  ::= { mGuardSECStickRemoteFWRuleEntry 5 }

-- SECSTICK_REMOTE_ACCESS_RULES.FROM_IP
mGuardSECStickFWsourceIP OBJECT-TYPE
  SYNTAX DisplayString
  ACCESS read-write
  STATUS mandatory
  DESCRIPTION
    "Variable name: SECSTICK_REMOTE_ACCESS_RULES.FROM_IP
    WebUi Label: From IP
    The rule's source IP address"
  ::= { mGuardSECStickRemoteFWRuleEntry 2 }

-- SECSTICK_REMOTE_ACCESS_RULES.INTERFACE_DEV
mGuardSECStickFWinterface OBJECT-TYPE
  SYNTAX INTEGER {
    extern(1),
    intern(2),
    extern2(3),
    dialin(4),
    viaipsec(5),
    dmz0(6),
    viagre(7)
  }
  ACCESS read-write
  STATUS mandatory
  DESCRIPTION
    "Variable name: SECSTICK_REMOTE_ACCESS_RULES.INTERFACE_DEV
    WebUi Label: Interface
    The network interface the rule belongs to (extern/intern/dmz)."
  ::= { mGuardSECStickRemoteFWRuleEntry 3 }

-- SECSTICK_REMOTE_ACCESS_RULES.FROM_MAC
mGuardSECStickFWfromMAC OBJECT-TYPE
  SYNTAX MacAddress
  ACCESS read-write
  STATUS mandatory
  DESCRIPTION
    "Variable name: SECSTICK_REMOTE_ACCESS_RULES.FROM_MAC
    WebUi Label: From MAC
    The rule's source MAC address."
  ::= { mGuardSECStickRemoteFWRuleEntry 8 }

-- SECSTICK_REMOTE_ACCESS_RULES.TARGET
mGuardSECStickFWtarget OBJECT-TYPE
  SYNTAX INTEGER {
    accept(1),
    reject(2),
    drop(3)
  }
  ACCESS read-write
  STATUS mandatory
  DESCRIPTION
    "Variable name: SECSTICK_REMOTE_ACCESS_RULES.TARGET
    WebUi Label: Action
    The target of the rule (accept/reject/drop)."
  ::= { mGuardSECStickRemoteFWRuleEntry 4 }

-- SECSTICK_REMOTE_ENABLE
mGuardSECStickRemoteEnable OBJECT-TYPE
  SYNTAX INTEGER {
    yes(1),
    no(2)
  }
  ACCESS read-write
  STATUS mandatory
  DESCRIPTION
    "Variable name: SECSTICK_REMOTE_ENABLE
    WebUi Label: Enable SEC-Stick remote access
    Enable SEC-Stick access from remote."
  ::= { mGuardSECStick 2 }

-- SECSTICK_REMOTE_LISTENPORT
mGuardSECStickRemotePort OBJECT-TYPE
  SYNTAX DisplayString
  ACCESS read-write
  STATUS mandatory
  DESCRIPTION
    "Variable name: SECSTICK_REMOTE_LISTENPORT
    WebUi Label: Remote SEC-Stick TCP port
    Port for SEC-Stick remote access (regularly 22002), service names
    allowed."
  ::= { mGuardSECStick 3 }

-- SECSTICK_VPN_HUBANDSPOKE
mGuardSECVPNHubAndSpoke OBJECT-TYPE
  SYNTAX INTEGER {
    yes(1),
    no(2)
  }
  ACCESS read-write
  STATUS mandatory
  DESCRIPTION
    "Variable name: SECSTICK_VPN_HUBANDSPOKE
    WebUi Label: Allow SEC-Stick forwarding into VPN tunnel
    Allow SEC-Stick connections to be forwarded into VPN."
  ::= { mGuardSECStick 11 }

-- SERIAL_BAUDRATE
mGuardSerialBaud OBJECT-TYPE
  SYNTAX INTEGER
  ACCESS read-write
  STATUS mandatory
  DESCRIPTION
    "Variable name: SERIAL_BAUDRATE
    WebUi Label: Baud rate
    Baud rate for the serial line. Possible values are 9600, 19200, 38400,
    57600"
  ::= { mGuardSerial 1 }

-- SERIAL_CONSOLE_VIA_USB_ENABLE
mGuardSerialConsoleViaUSB OBJECT-TYPE
  SYNTAX INTEGER {
    yes(1),
    no(2)
  }
  ACCESS read-write
  STATUS mandatory
  DESCRIPTION
    "Variable name: SERIAL_CONSOLE_VIA_USB_ENABLE
    WebUi Label: Serial console via USB
    Enable hardware handshake"
  ::= { mGuardSerialPPP 10 }

-- SERIAL_CRTSCTS
mGuardSerialHWHandshakeEnable OBJECT-TYPE
  SYNTAX INTEGER {
    enabled(1),
    disabled(2)
  }
  ACCESS read-write
  STATUS mandatory
  DESCRIPTION
    "Variable name: SERIAL_CRTSCTS
    WebUi Label: Hardware handshake RTS/CTS
    Enable hardware handshake"
  ::= { mGuardSerial 2 }

-- SERIAL_FW_INCOMING
mGuardSerialPPPFWINuuid OBJECT-TYPE
  SYNTAX DisplayString
  ACCESS read-only
  STATUS mandatory
  DESCRIPTION
    "Variable name: SERIAL_FW_INCOMING
    WebUi Label: Incoming firewall rules (serial interface)
    Universally Unique Identifier (UUID, RFC 4122) used for
    mGuardSerialPPPFWINTable logging"
  ::= { mGuardSerialPPPFWIN 3 }


-- SERIAL_FW_INCOMING table
mGuardSerialPPPFWINTable OBJECT-TYPE
  SYNTAX SEQUENCE OF MGuardSerialPPPFWINEntry
  ACCESS not-accessible
  STATUS mandatory
  DESCRIPTION
    "A table of SERIAL_FW_INCOMING"
  ::= { mGuardSerialPPPFWIN 1 }

-- SERIAL_FW_INCOMING table entry
mGuardSerialPPPFWINEntry OBJECT-TYPE
  SYNTAX MGuardSerialPPPFWINEntry
  ACCESS not-accessible
  STATUS mandatory
  DESCRIPTION
    "An entry of SERIAL_FW_INCOMING"
  INDEX { mGuardSerialPPPFWINruleIndex }
  ::= { mGuardSerialPPPFWINTable 1 }

MGuardSerialPPPFWINEntry ::= SEQUENCE {
  mGuardSerialPPPFWINruleIndex             INTEGER,
  mGuardSerialPPPFWINsourceIP              DisplayString,
  mGuardSerialPPPFWINdestinationIP         DisplayString,
  mGuardSerialPPPFWINsport                 DisplayString,
  mGuardSerialPPPFWINdport                 DisplayString,
  mGuardSerialPPPFWINtargetValue           INTEGER,
  mGuardSerialPPPFWINproto                 INTEGER,
  mGuardSerialPPPFWINlog                   INTEGER,
  mGuardSerialPPPFWINRowStatus             RowStatus,
  mGuardSerialPPPFWINcomment               DisplayString,
  mGuardSerialPPPFWINtargetRef             OBJECT IDENTIFIER
}

-- SERIAL_FW_INCOMING table index
mGuardSerialPPPFWINruleIndex OBJECT-TYPE
  SYNTAX INTEGER (1..2147483647)
  ACCESS not-accessible
  STATUS mandatory
  DESCRIPTION
    "Index to SERIAL_FW_INCOMING"
  ::= { mGuardSerialPPPFWINEntry 1 }

-- SERIAL_FW_INCOMING row status
mGuardSerialPPPFWINRowStatus OBJECT-TYPE
  SYNTAX RowStatus
  ACCESS read-write
  STATUS mandatory
  DESCRIPTION
    "RowStatus of SERIAL_FW_INCOMING"
  ::= { mGuardSerialPPPFWINEntry 9 }

-- SERIAL_FW_INCOMING.COMMENT
mGuardSerialPPPFWINcomment OBJECT-TYPE
  SYNTAX DisplayString
  ACCESS read-write
  STATUS mandatory
  DESCRIPTION
    "Variable name: SERIAL_FW_INCOMING.COMMENT
    WebUi Label: Comment
    Commentary or name for this rule."
  ::= { mGuardSerialPPPFWINEntry 10 }

-- SERIAL_FW_INCOMING.FROM_PORT
mGuardSerialPPPFWINsport OBJECT-TYPE
  SYNTAX DisplayString
  ACCESS read-write
  STATUS mandatory
  DESCRIPTION
    "Variable name: SERIAL_FW_INCOMING.FROM_PORT
    WebUi Label: From port
    The rule's source port"
  ::= { mGuardSerialPPPFWINEntry 4 }

-- SERIAL_FW_INCOMING.LOG
mGuardSerialPPPFWINlog OBJECT-TYPE
  SYNTAX INTEGER {
    yes(1),
    no(2)
  }
  ACCESS read-write
  STATUS mandatory
  DESCRIPTION
    "Variable name: SERIAL_FW_INCOMING.LOG
    WebUi Label: Log
    Log packets matching this rule ?"
  ::= { mGuardSerialPPPFWINEntry 8 }

-- SERIAL_FW_INCOMING.PROTO
mGuardSerialPPPFWINproto OBJECT-TYPE
  SYNTAX INTEGER {
    tcp(1),
    udp(2),
    icmp(3),
    all(4),
    gre(5)
  }
  ACCESS read-write
  STATUS mandatory
  DESCRIPTION
    "Variable name: SERIAL_FW_INCOMING.PROTO
    WebUi Label: Protocol
    The rule's protocol"
  ::= { mGuardSerialPPPFWINEntry 7 }

-- SERIAL_FW_INCOMING.FROM_IP
mGuardSerialPPPFWINsourceIP OBJECT-TYPE
  SYNTAX DisplayString
  ACCESS read-write
  STATUS mandatory
  DESCRIPTION
    "Variable name: SERIAL_FW_INCOMING.FROM_IP
    WebUi Label: From IP
    The rule's source IP address"
  ::= { mGuardSerialPPPFWINEntry 2 }

-- SERIAL_FW_INCOMING.IN_IP
mGuardSerialPPPFWINdestinationIP OBJECT-TYPE
  SYNTAX DisplayString
  ACCESS read-write
  STATUS mandatory
  DESCRIPTION
    "Variable name: SERIAL_FW_INCOMING.IN_IP
    WebUi Label: To IP
    The rule's source IP address"
  ::= { mGuardSerialPPPFWINEntry 3 }

-- SERIAL_FW_INCOMING.TARGET_REF
mGuardSerialPPPFWINtargetValue OBJECT-TYPE
  SYNTAX INTEGER {
    accept(1),
    reject(2),
    drop(3)
  }
  ACCESS read-write
  STATUS mandatory
  DESCRIPTION
    "Variable name: SERIAL_FW_INCOMING.TARGET_REF
    WebUi Label: Action
    The rule's target"
  ::= { mGuardSerialPPPFWINEntry 6 }

-- SERIAL_FW_INCOMING.TARGET_REF reference
mGuardSerialPPPFWINtargetRef OBJECT-TYPE
  SYNTAX OBJECT IDENTIFIER
  ACCESS read-write
  STATUS mandatory
  DESCRIPTION
    "Variable name: SERIAL_FW_INCOMING.TARGET_REF
    WebUi Label: Action
    "
  ::= { mGuardSerialPPPFWINEntry 11 }

-- SERIAL_FW_INCOMING.IN_PORT
mGuardSerialPPPFWINdport OBJECT-TYPE
  SYNTAX DisplayString
  ACCESS read-write
  STATUS mandatory
  DESCRIPTION
    "Variable name: SERIAL_FW_INCOMING.IN_PORT
    WebUi Label: To port
    The rule's destination port"
  ::= { mGuardSerialPPPFWINEntry 5 }

-- SERIAL_FW_LOG_DEFAULT_INCOMING
mGuardSerialPPPFWINLogDefault OBJECT-TYPE
  SYNTAX INTEGER {
    yes(1),
    no(2)
  }
  ACCESS read-write
  STATUS mandatory
  DESCRIPTION
    "Variable name: SERIAL_FW_LOG_DEFAULT_INCOMING
    WebUi Label: Log entries for unknown connection attempts
    Log entries for undefined incoming connection attempts?"
  ::= { mGuardSerialPPPFWIN 2 }

-- SERIAL_FW_LOG_DEFAULT_OUTGOING
mGuardSerialPPPFWOUTLogDefault OBJECT-TYPE
  SYNTAX INTEGER {
    yes(1),
    no(2)
  }
  ACCESS read-write
  STATUS mandatory
  DESCRIPTION
    "Variable name: SERIAL_FW_LOG_DEFAULT_OUTGOING
    WebUi Label: Log entries for unknown connection attempts
    Log entries for unknown outgoing connection attempts?"
  ::= { mGuardSerialPPPFWOUT 2 }

-- SERIAL_FW_OUTGOING
mGuardSerialPPPFWOUTuuid OBJECT-TYPE
  SYNTAX DisplayString
  ACCESS read-only
  STATUS mandatory
  DESCRIPTION
    "Variable name: SERIAL_FW_OUTGOING
    WebUi Label: Outgoing firewall rules (serial interface)
    Universally Unique Identifier (UUID, RFC 4122) used for
    mGuardSerialPPPFWOUTTable logging"
  ::= { mGuardSerialPPPFWOUT 3 }


-- SERIAL_FW_OUTGOING table
mGuardSerialPPPFWOUTTable OBJECT-TYPE
  SYNTAX SEQUENCE OF MGuardSerialPPPFWOUTEntry
  ACCESS not-accessible
  STATUS mandatory
  DESCRIPTION
    "A table of SERIAL_FW_OUTGOING"
  ::= { mGuardSerialPPPFWOUT 1 }

-- SERIAL_FW_OUTGOING table entry
mGuardSerialPPPFWOUTEntry OBJECT-TYPE
  SYNTAX MGuardSerialPPPFWOUTEntry
  ACCESS not-accessible
  STATUS mandatory
  DESCRIPTION
    "An entry of SERIAL_FW_OUTGOING"
  INDEX { mGuardSerialPPPFWOUTruleIndex }
  ::= { mGuardSerialPPPFWOUTTable 1 }

MGuardSerialPPPFWOUTEntry ::= SEQUENCE {
  mGuardSerialPPPFWOUTruleIndex            INTEGER,
  mGuardSerialPPPFWOUTsourceIP             DisplayString,
  mGuardSerialPPPFWOUTtargetIP             DisplayString,
  mGuardSerialPPPFWOUTsport                DisplayString,
  mGuardSerialPPPFWOUTdport                DisplayString,
  mGuardSerialPPPFWOUTtarget               INTEGER,
  mGuardSerialPPPFWOUTproto                INTEGER,
  mGuardSerialPPPFWOUTlog                  INTEGER,
  mGuardSerialPPPFWOUTRowStatus            RowStatus,
  mGuardSerialPPPFWOUTcomment              DisplayString,
  mGuardSerialPPPFWOUTtargetRef            OBJECT IDENTIFIER
}

-- SERIAL_FW_OUTGOING table index
mGuardSerialPPPFWOUTruleIndex OBJECT-TYPE
  SYNTAX INTEGER (1..2147483647)
  ACCESS not-accessible
  STATUS mandatory
  DESCRIPTION
    "Index to SERIAL_FW_OUTGOING"
  ::= { mGuardSerialPPPFWOUTEntry 1 }

-- SERIAL_FW_OUTGOING row status
mGuardSerialPPPFWOUTRowStatus OBJECT-TYPE
  SYNTAX RowStatus
  ACCESS read-write
  STATUS mandatory
  DESCRIPTION
    "RowStatus of SERIAL_FW_OUTGOING"
  ::= { mGuardSerialPPPFWOUTEntry 9 }

-- SERIAL_FW_OUTGOING.COMMENT
mGuardSerialPPPFWOUTcomment OBJECT-TYPE
  SYNTAX DisplayString
  ACCESS read-write
  STATUS mandatory
  DESCRIPTION
    "Variable name: SERIAL_FW_OUTGOING.COMMENT
    WebUi Label: Comment
    Commentary or name for this rule."
  ::= { mGuardSerialPPPFWOUTEntry 10 }

-- SERIAL_FW_OUTGOING.FROM_PORT
mGuardSerialPPPFWOUTsport OBJECT-TYPE
  SYNTAX DisplayString
  ACCESS read-write
  STATUS mandatory
  DESCRIPTION
    "Variable name: SERIAL_FW_OUTGOING.FROM_PORT
    WebUi Label: From port
    The rule's source port"
  ::= { mGuardSerialPPPFWOUTEntry 4 }

-- SERIAL_FW_OUTGOING.LOG
mGuardSerialPPPFWOUTlog OBJECT-TYPE
  SYNTAX INTEGER {
    yes(1),
    no(2)
  }
  ACCESS read-write
  STATUS mandatory
  DESCRIPTION
    "Variable name: SERIAL_FW_OUTGOING.LOG
    WebUi Label: Log
    Log packets matching this rule ?"
  ::= { mGuardSerialPPPFWOUTEntry 8 }

-- SERIAL_FW_OUTGOING.PROTO
mGuardSerialPPPFWOUTproto OBJECT-TYPE
  SYNTAX INTEGER {
    tcp(1),
    udp(2),
    icmp(3),
    all(4),
    gre(5)
  }
  ACCESS read-write
  STATUS mandatory
  DESCRIPTION
    "Variable name: SERIAL_FW_OUTGOING.PROTO
    WebUi Label: Protocol
    The rule's protocol"
  ::= { mGuardSerialPPPFWOUTEntry 7 }

-- SERIAL_FW_OUTGOING.FROM_IP
mGuardSerialPPPFWOUTsourceIP OBJECT-TYPE
  SYNTAX DisplayString
  ACCESS read-write
  STATUS mandatory
  DESCRIPTION
    "Variable name: SERIAL_FW_OUTGOING.FROM_IP
    WebUi Label: From IP
    The rule's source IP address"
  ::= { mGuardSerialPPPFWOUTEntry 2 }

-- SERIAL_FW_OUTGOING.IN_IP
mGuardSerialPPPFWOUTtargetIP OBJECT-TYPE
  SYNTAX DisplayString
  ACCESS read-write
  STATUS mandatory
  DESCRIPTION
    "Variable name: SERIAL_FW_OUTGOING.IN_IP
    WebUi Label: To IP
    The rule's source IP address"
  ::= { mGuardSerialPPPFWOUTEntry 3 }

-- SERIAL_FW_OUTGOING.TARGET_REF
mGuardSerialPPPFWOUTtarget OBJECT-TYPE
  SYNTAX INTEGER {
    accept(1),
    reject(2),
    drop(3)
  }
  ACCESS read-write
  STATUS mandatory
  DESCRIPTION
    "Variable name: SERIAL_FW_OUTGOING.TARGET_REF
    WebUi Label: Action
    The rule's target"
  ::= { mGuardSerialPPPFWOUTEntry 6 }

-- SERIAL_FW_OUTGOING.TARGET_REF reference
mGuardSerialPPPFWOUTtargetRef OBJECT-TYPE
  SYNTAX OBJECT IDENTIFIER
  ACCESS read-write
  STATUS mandatory
  DESCRIPTION
    "Variable name: SERIAL_FW_OUTGOING.TARGET_REF
    WebUi Label: Action
    "
  ::= { mGuardSerialPPPFWOUTEntry 11 }

-- SERIAL_FW_OUTGOING.IN_PORT
mGuardSerialPPPFWOUTdport OBJECT-TYPE
  SYNTAX DisplayString
  ACCESS read-write
  STATUS mandatory
  DESCRIPTION
    "Variable name: SERIAL_FW_OUTGOING.IN_PORT
    WebUi Label: To port
    The rule's destination port"
  ::= { mGuardSerialPPPFWOUTEntry 5 }

-- SERIAL_PARAMS
mGuardSerialParams OBJECT-TYPE
  SYNTAX INTEGER {
    n1(1),
    e1(2),
    o1(3),
    n2(4),
    e2(5),
    o2(6),
    n17(7),
    e17(8),
    o17(9),
    n27(10),
    e27(11),
    o27(12)
  }
  ACCESS read-write
  STATUS mandatory
  DESCRIPTION
    "Variable name: SERIAL_PARAMS
    WebUi Label: Serial parameters
    Defines character size, parity and stop bits of the serial port"
  ::= { mGuardSerialPPP 11 }

-- SERIAL_PPP_IP_LOCAL
mGuardSerialPPPLocalIP OBJECT-TYPE
  SYNTAX IpAddress
  ACCESS read-write
  STATUS mandatory
  DESCRIPTION
    "Variable name: SERIAL_PPP_IP_LOCAL
    WebUi Label: Local IP
    Local IP address for PPP."
  ::= { mGuardSerialPPP 4 }

-- SERIAL_PPP_IP_REMOTE
mGuardSerialPPPRemoteIP OBJECT-TYPE
  SYNTAX IpAddress
  ACCESS read-write
  STATUS mandatory
  DESCRIPTION
    "Variable name: SERIAL_PPP_IP_REMOTE
    WebUi Label: Remote IP
    Remote IP address for PPP."
  ::= { mGuardSerialPPP 5 }

-- SERIAL_PPP_LOGIN
mGuardSerialPPPLogin OBJECT-TYPE
  SYNTAX DisplayString
  ACCESS read-write
  STATUS mandatory
  DESCRIPTION
    "Variable name: SERIAL_PPP_LOGIN
    WebUi Label: PPP login
    Login for Serial PPP."
  ::= { mGuardSerialPPP 2 }

-- SERIAL_PPP_MODEM
mGuardSerialPPPModem OBJECT-TYPE
  SYNTAX INTEGER {
    off(1),
    internal(2),
    external(3)
  }
  ACCESS read-write
  STATUS mandatory
  DESCRIPTION
    "Variable name: SERIAL_PPP_MODEM
    WebUi Label: Modem (PPP)
    Select PPP device"
  ::= { mGuardSerialPPP 8 }

-- SERIAL_PPP_PASSWORD
mGuardSerialPPPPasswd OBJECT-TYPE
  SYNTAX DisplayString
  ACCESS read-write
  STATUS mandatory
  DESCRIPTION
    "Variable name: SERIAL_PPP_PASSWORD
    WebUi Label: PPP password
    Password for Serial PPP."
  ::= { mGuardSerialPPP 3 }

-- SERIAL_TRANSPARENT
mGuardSerialPPPTransparent OBJECT-TYPE
  SYNTAX INTEGER {
    yes(1),
    no(2)
  }
  ACCESS read-write
  STATUS mandatory
  DESCRIPTION
    "Variable name: SERIAL_TRANSPARENT
    WebUi Label: Handle modem transparently (for dial-in only)
    Transparent access to the modem for dial-in over the external serial
    line with an optional modem"
  ::= { mGuardSerialPPP 9 }

-- SERVICE_ACK1_REF
mGuardServiceAck1Value OBJECT-TYPE
  SYNTAX INTEGER {
    none(1)
  }
  ACCESS read-write
  STATUS mandatory
  DESCRIPTION
    "Variable name: SERVICE_ACK1_REF
    WebUi Label: Monitor VPN connection or firewall rule record
    This object is effective if and only if the 'mGuardServiceAck1Ref'
    object contains its OID. When this object is read, it always returns
    the value 'none'. When the value 'none' is written to this object, the
    feature to signal the status of a VPN connection or a firewall rule
    record with the Service1 ACK contact and the INFO1 LED is disabled."
  ::= { mGuardService 2 }

-- SERVICE_ACK1_REF reference
mGuardServiceAck1Ref OBJECT-TYPE
  SYNTAX OBJECT IDENTIFIER
  ACCESS read-write
  STATUS mandatory
  DESCRIPTION
    "Variable name: SERVICE_ACK1_REF
    WebUi Label: Monitor VPN connection or firewall rule record
    When this object contains the OID of a 'mGuardVPNconIndex' or
    'mGuardOpenVPNConnectionIndex' object, signal the status of the VPN
    connection with the Service1 ACK contact and the INFO1 LED. When it
    contains the OID of an 'mGuardFWRuleIndex' object, signal the status
    of the firewall rule record. When it contains the OID of the
    'mGuardServiceAck1Value' object, this feature is disabled. To monitor
    a VPN connection or firewall rule record in this manner, write the OID
    of the corresponding 'mGuardVPNconIndex',
    'mGuardOpenVPNConnectionIndex' or 'mGuardFWRuleIndex'object to this
    object. To disable this feature, set the 'mGuardServiceAck1Value'
    object."
  ::= { mGuardService 1 }

-- SERVICE_ACK2_REF
mGuardServiceAck2Value OBJECT-TYPE
  SYNTAX INTEGER {
    none(1)
  }
  ACCESS read-write
  STATUS mandatory
  DESCRIPTION
    "Variable name: SERVICE_ACK2_REF
    WebUi Label: Monitor VPN connection or firewall rule record
    This object is effective if and only if the 'mGuardServiceAck2Ref'
    object contains its OID. When this object is read, it always returns
    the value 'none'. When the value 'none' is written to this object, the
    feature to signal the status of a VPN connection or a firewall rule
    record with the Service2 ACK contact and the INFO2 LED is disabled."
  ::= { mGuardService 4 }

-- SERVICE_ACK2_REF reference
mGuardServiceAck2Ref OBJECT-TYPE
  SYNTAX OBJECT IDENTIFIER
  ACCESS read-write
  STATUS mandatory
  DESCRIPTION
    "Variable name: SERVICE_ACK2_REF
    WebUi Label: Monitor VPN connection or firewall rule record
    When this object contains the OID of a 'mGuardVPNconIndex' or
    'mGuardOpenVPNConnectionIndex' object, signal the status of the VPN
    connection with the Service2 ACK contact and the INFO2 LED. When it
    contains the OID of an 'mGuardFWRuleIndex' object, signal the status
    of the firewall rule record. When it contains the OID of the
    'mGuardServiceAck2Value' object, this feature is disabled. To monitor
    a VPN connection or firewall rule record in this manner, write the OID
    of the corresponding 'mGuardVPNconIndex',
    'mGuardOpenVPNConnectionIndex' or 'mGuardFWRuleIndex'object to this
    object. To disable this feature, set the 'mGuardServiceAck2Value'
    object."
  ::= { mGuardService 3 }

-- SERVICE_SWITCH1_TYPE
mGuardVPNSwitch1Type OBJECT-TYPE
  SYNTAX INTEGER {
    button(1),
    switch(2)
  }
  ACCESS read-write
  STATUS mandatory
  DESCRIPTION
    "Variable name: SERVICE_SWITCH1_TYPE
    WebUi Label: Switch type connected to the input
    Use button mode (push to initiate) or switch mode (keep contact in
    position) to control VPN connection."
  ::= { mGuardVPNSettings 15 }

-- SERVICE_SWITCH2_TYPE
mGuardVPNSwitch2Type OBJECT-TYPE
  SYNTAX INTEGER {
    button(1),
    switch(2)
  }
  ACCESS read-write
  STATUS mandatory
  DESCRIPTION
    "Variable name: SERVICE_SWITCH2_TYPE
    WebUi Label: Switch type connected to the input
    Use button mode (push to initiate) or switch mode (keep contact in
    position) to control VPN connection."
  ::= { mGuardVPNSettings 32 }

-- SERVICE_SWITCH3_TYPE
mGuardVPNSwitch3Type OBJECT-TYPE
  SYNTAX INTEGER {
    button(1),
    switch(2)
  }
  ACCESS read-write
  STATUS mandatory
  DESCRIPTION
    "Variable name: SERVICE_SWITCH3_TYPE
    WebUi Label: Switch type connected to the input
    Use button mode (push to initiate) or switch mode (keep contact in
    position) to control VPN connection."
  ::= { mGuardVPNSettings 33 }

-- SHELL_TIMEOUT
mGuardSSHTimeout OBJECT-TYPE
  SYNTAX INTEGER(0..86400)
  ACCESS read-write
  STATUS mandatory
  DESCRIPTION
    "Variable name: SHELL_TIMEOUT
    WebUi Label: Session timeout
    Shell timeout after inactivity."
  ::= { mGuardSSHRemoteAccess 6 }

-- SIG_ALARM_LINK
mGuardTResSignalRelaisNetworkLinkAlarm OBJECT-TYPE
  SYNTAX INTEGER {
    on(1),
    off(2)
  }
  ACCESS read-write
  STATUS mandatory
  DESCRIPTION
    "Variable name: SIG_ALARM_LINK
    WebUi Label: Link supervision
    Enables/disables an alarm depending on the link state of the network
    interfaces. Link alarms for each interface may be configured via
    mGuardTResSignalLinkTable"
  ::= { mGuardTResSignalRelais 10 }


-- SMS_NOTIFICATION table
mGuardSmsNotificationTable OBJECT-TYPE
  SYNTAX SEQUENCE OF MGuardSmsNotificationEntry
  ACCESS not-accessible
  STATUS mandatory
  DESCRIPTION
    "A table of SMS_NOTIFICATION"
  ::= { mGuardGsm 8 }

-- SMS_NOTIFICATION table entry
mGuardSmsNotificationEntry OBJECT-TYPE
  SYNTAX MGuardSmsNotificationEntry
  ACCESS not-accessible
  STATUS mandatory
  DESCRIPTION
    "An entry of SMS_NOTIFICATION"
  INDEX { mGuardSmsNotificationIndex }
  ::= { mGuardSmsNotificationTable 1 }

MGuardSmsNotificationEntry ::= SEQUENCE {
  mGuardSmsNotificationIndex               INTEGER,
  mGuardSmsNotificationRowStatus           RowStatus,
  mGuardSmsNotificationTo                  DisplayString,
  mGuardSmsNotificationMessage             DisplayString,
  mGuardSmsNotificationEvent               DisplayString,
  mGuardSmsNotificationSelectorValue       INTEGER,
  mGuardSmsNotificationSelectorRef         OBJECT IDENTIFIER,
  mGuardSmsNotificationFWRuleValue         INTEGER,
  mGuardSmsNotificationFWRuleRef           OBJECT IDENTIFIER,
  mGuardSmsNotificationOpenVPNValue        INTEGER,
  mGuardSmsNotificationOpenVPNRef          OBJECT IDENTIFIER
}

-- SMS_NOTIFICATION table index
mGuardSmsNotificationIndex OBJECT-TYPE
  SYNTAX INTEGER (1..2147483647)
  ACCESS not-accessible
  STATUS mandatory
  DESCRIPTION
    "Index to SMS_NOTIFICATION"
  ::= { mGuardSmsNotificationEntry 1 }

-- SMS_NOTIFICATION row status
mGuardSmsNotificationRowStatus OBJECT-TYPE
  SYNTAX RowStatus
  ACCESS read-write
  STATUS mandatory
  DESCRIPTION
    "RowStatus of SMS_NOTIFICATION"
  ::= { mGuardSmsNotificationEntry 2 }

-- SMS_NOTIFICATION.SELECTOR_OPENVPN
mGuardSmsNotificationOpenVPNValue OBJECT-TYPE
  SYNTAX INTEGER {
    none(1)
  }
  ACCESS read-write
  STATUS mandatory
  DESCRIPTION
    "Variable name: SMS_NOTIFICATION.SELECTOR_OPENVPN
    WebUi Label: Selector
    "
  ::= { mGuardSmsNotificationEntry 11 }

-- SMS_NOTIFICATION.SELECTOR_OPENVPN reference
mGuardSmsNotificationOpenVPNRef OBJECT-TYPE
  SYNTAX OBJECT IDENTIFIER
  ACCESS read-write
  STATUS mandatory
  DESCRIPTION
    "Variable name: SMS_NOTIFICATION.SELECTOR_OPENVPN
    WebUi Label: Selector
    "
  ::= { mGuardSmsNotificationEntry 12 }

-- SMS_NOTIFICATION.SELECTOR
mGuardSmsNotificationSelectorValue OBJECT-TYPE
  SYNTAX INTEGER {
    none(1)
  }
  ACCESS read-write
  STATUS mandatory
  DESCRIPTION
    "Variable name: SMS_NOTIFICATION.SELECTOR
    WebUi Label: Selector
    Configures the VPN connection to watch"
  ::= { mGuardSmsNotificationEntry 6 }

-- SMS_NOTIFICATION.SELECTOR reference
mGuardSmsNotificationSelectorRef OBJECT-TYPE
  SYNTAX OBJECT IDENTIFIER
  ACCESS read-write
  STATUS mandatory
  DESCRIPTION
    "Variable name: SMS_NOTIFICATION.SELECTOR
    WebUi Label: Selector
    When this object contains the OID of an 'mGuardVPNconIndex' or
    'mGuardOpenVPNConnectionIndex' object, the corresponding connection is
    used for this notification. To disable this feature, set the OID of
    the 'mGuardSmsNotificationSelectorValue' object."
  ::= { mGuardSmsNotificationEntry 7 }

-- SMS_NOTIFICATION.TO
mGuardSmsNotificationTo OBJECT-TYPE
  SYNTAX DisplayString
  ACCESS read-write
  STATUS mandatory
  DESCRIPTION
    "Variable name: SMS_NOTIFICATION.TO
    WebUi Label: Text message recipient number
    Sets the receiver mobile number"
  ::= { mGuardSmsNotificationEntry 3 }

-- SMS_NOTIFICATION.SELECTOR_FW_RULESET
mGuardSmsNotificationFWRuleValue OBJECT-TYPE
  SYNTAX INTEGER {
    none(1)
  }
  ACCESS read-write
  STATUS mandatory
  DESCRIPTION
    "Variable name: SMS_NOTIFICATION.SELECTOR_FW_RULESET
    WebUi Label: Selector
    When read, this object will always return the value 'none'. When the
    value 'none' is written to this object, any association of this
    notification with a firewall rule set will be deleted from the
    'mGuardSmsNotificationFWRuleRef' object."
  ::= { mGuardSmsNotificationEntry 8 }

-- SMS_NOTIFICATION.SELECTOR_FW_RULESET reference
mGuardSmsNotificationFWRuleRef OBJECT-TYPE
  SYNTAX OBJECT IDENTIFIER
  ACCESS read-write
  STATUS mandatory
  DESCRIPTION
    "Variable name: SMS_NOTIFICATION.SELECTOR_FW_RULESET
    WebUi Label: Selector
    Set this object to an 'mGuardFWRuleIndex' object to associate this
    notification with a firewall rule set. Set the object
    'mGuardSmsNotificationFWRuleValue to disable this association. For
    this feature to work, you also have to set the object
    'mGuardSmsNotificationEvent' appropriately."
  ::= { mGuardSmsNotificationEntry 9 }

-- SMS_NOTIFICATION.MESSAGE
mGuardSmsNotificationMessage OBJECT-TYPE
  SYNTAX DisplayString
  ACCESS read-write
  STATUS mandatory
  DESCRIPTION
    "Variable name: SMS_NOTIFICATION.MESSAGE
    WebUi Label: Text message content
    Sets the message to be send"
  ::= { mGuardSmsNotificationEntry 4 }

-- SMS_NOTIFICATION.EVENT
mGuardSmsNotificationEvent OBJECT-TYPE
  SYNTAX DisplayString
  ACCESS read-write
  STATUS mandatory
  DESCRIPTION
    "Variable name: SMS_NOTIFICATION.EVENT
    WebUi Label: Event
    Configures the event which will initiate sending this SMS"
  ::= { mGuardSmsNotificationEntry 5 }

-- SNMP_ACCESS_RULES
mGuardSNMPRemoteUUID OBJECT-TYPE
  SYNTAX DisplayString
  ACCESS read-only
  STATUS mandatory
  DESCRIPTION
    "Variable name: SNMP_ACCESS_RULES
    WebUi Label: Allowed networks
    Universally Unique Identifier (UUID, RFC 4122) used for
    mGuardSNMPFWRuleTable logging."
  ::= { mGuardSNMP 9 }


-- SNMP_ACCESS_RULES table
mGuardSNMPFWRuleTable OBJECT-TYPE
  SYNTAX SEQUENCE OF MGuardSNMPFWRuleEntry
  ACCESS not-accessible
  STATUS mandatory
  DESCRIPTION
    "A table of SNMP_ACCESS_RULES"
  ::= { mGuardSNMP 6 }

-- SNMP_ACCESS_RULES table entry
mGuardSNMPFWRuleEntry OBJECT-TYPE
  SYNTAX MGuardSNMPFWRuleEntry
  ACCESS not-accessible
  STATUS mandatory
  DESCRIPTION
    "An entry of SNMP_ACCESS_RULES"
  INDEX { mGuardSNMPFWruleIndex }
  ::= { mGuardSNMPFWRuleTable 1 }

MGuardSNMPFWRuleEntry ::= SEQUENCE {
  mGuardSNMPFWruleIndex                    INTEGER,
  mGuardSNMPFWsourceIP                     DisplayString,
  mGuardSNMPFWinterface                    INTEGER,
  mGuardSNMPFWtarget                       INTEGER,
  mGuardSNMPFWlog                          INTEGER,
  mGuardSNMPFWRowStatus                    RowStatus,
  mGuardSNMPFWcomment                      DisplayString,
  mGuardSNMPFWfromMAC                      MacAddress
}

-- SNMP_ACCESS_RULES table index
mGuardSNMPFWruleIndex OBJECT-TYPE
  SYNTAX INTEGER (1..2147483647)
  ACCESS not-accessible
  STATUS mandatory
  DESCRIPTION
    "Index to SNMP_ACCESS_RULES"
  ::= { mGuardSNMPFWRuleEntry 1 }

-- SNMP_ACCESS_RULES row status
mGuardSNMPFWRowStatus OBJECT-TYPE
  SYNTAX RowStatus
  ACCESS read-write
  STATUS mandatory
  DESCRIPTION
    "RowStatus of SNMP_ACCESS_RULES"
  ::= { mGuardSNMPFWRuleEntry 6 }

-- SNMP_ACCESS_RULES.COMMENT
mGuardSNMPFWcomment OBJECT-TYPE
  SYNTAX DisplayString
  ACCESS read-write
  STATUS mandatory
  DESCRIPTION
    "Variable name: SNMP_ACCESS_RULES.COMMENT
    WebUi Label: Comment
    Commentary or name for this rule."
  ::= { mGuardSNMPFWRuleEntry 7 }

-- SNMP_ACCESS_RULES.LOG
mGuardSNMPFWlog OBJECT-TYPE
  SYNTAX INTEGER {
    yes(1),
    no(2)
  }
  ACCESS read-write
  STATUS mandatory
  DESCRIPTION
    "Variable name: SNMP_ACCESS_RULES.LOG
    WebUi Label: Log
    Log packets matching this rule ?"
  ::= { mGuardSNMPFWRuleEntry 5 }

-- SNMP_ACCESS_RULES.FROM_IP
mGuardSNMPFWsourceIP OBJECT-TYPE
  SYNTAX DisplayString
  ACCESS read-write
  STATUS mandatory
  DESCRIPTION
    "Variable name: SNMP_ACCESS_RULES.FROM_IP
    WebUi Label: From IP
    The rule's source IP address"
  ::= { mGuardSNMPFWRuleEntry 2 }

-- SNMP_ACCESS_RULES.INTERFACE_DEV
mGuardSNMPFWinterface OBJECT-TYPE
  SYNTAX INTEGER {
    extern(1),
    intern(2),
    extern2(3),
    dialin(4),
    viaipsec(5),
    dmz0(6),
    viagre(7)
  }
  ACCESS read-write
  STATUS mandatory
  DESCRIPTION
    "Variable name: SNMP_ACCESS_RULES.INTERFACE_DEV
    WebUi Label: Interface
    The network interface the rule belongs to (extern/intern/dmz)."
  ::= { mGuardSNMPFWRuleEntry 3 }

-- SNMP_ACCESS_RULES.FROM_MAC
mGuardSNMPFWfromMAC OBJECT-TYPE
  SYNTAX MacAddress
  ACCESS read-write
  STATUS mandatory
  DESCRIPTION
    "Variable name: SNMP_ACCESS_RULES.FROM_MAC
    WebUi Label: From MAC
    The rule's source MAC address."
  ::= { mGuardSNMPFWRuleEntry 8 }

-- SNMP_ACCESS_RULES.TARGET
mGuardSNMPFWtarget OBJECT-TYPE
  SYNTAX INTEGER {
    accept(1),
    reject(2),
    drop(3)
  }
  ACCESS read-write
  STATUS mandatory
  DESCRIPTION
    "Variable name: SNMP_ACCESS_RULES.TARGET
    WebUi Label: Action
    The target of the rule (accept/reject/drop)."
  ::= { mGuardSNMPFWRuleEntry 4 }

-- SNMP_AGENT_TRAP
mGuardSNMPAgentTrapFlag OBJECT-TYPE
  SYNTAX INTEGER {
    yes(1),
    no(2)
  }
  ACCESS read-write
  STATUS mandatory
  DESCRIPTION
    "Variable name: SNMP_AGENT_TRAP
    WebUi Label: Agent (external config storage, temperature)
    Enables/Disables the traps with enterprise = hmAgent."
  ::= { mGuardSNMPTrapConfigGroup 6 }

-- SNMP_AUTHENTICATION_TRAP
mGuardSNMPAuthenticationTrapFlag OBJECT-TYPE
  SYNTAX INTEGER {
    yes(1),
    no(2)
  }
  ACCESS read-write
  STATUS mandatory
  DESCRIPTION
    "Variable name: SNMP_AUTHENTICATION_TRAP
    WebUi Label: SNMP authentication
    Authentication Flag - Enable/Disable SNMP authentication trap."
  ::= { mGuardSNMPTrapConfigGroup 1 }

-- SNMP_CHASSIS_TRAP
mGuardSNMPChassisTrapFlag OBJECT-TYPE
  SYNTAX INTEGER {
    yes(1),
    no(2)
  }
  ACCESS read-write
  STATUS mandatory
  DESCRIPTION
    "Variable name: SNMP_CHASSIS_TRAP
    WebUi Label: Chassis (power, signal relay)
    Enables/Disables the traps with enterprise = hmChassis."
  ::= { mGuardSNMPTrapConfigGroup 5 }

-- SNMP_COLDSTART_TRAP
mGuardSNMPColdStartTrapFlag OBJECT-TYPE
  SYNTAX INTEGER {
    yes(1),
    no(2)
  }
  ACCESS read-write
  STATUS mandatory
  DESCRIPTION
    "Variable name: SNMP_COLDSTART_TRAP
    WebUi Label: Coldstart
    ColdStart Flag - Enable/Disable SNMP coldstart trap."
  ::= { mGuardSNMPTrapConfigGroup 3 }

-- SNMP_COMMUNITY
mGuardSNMPv1RWCommunity OBJECT-TYPE
  SYNTAX DisplayString
  ACCESS read-write
  STATUS mandatory
  DESCRIPTION
    "Variable name: SNMP_COMMUNITY
    WebUi Label: Read-Write community
    Read-write community string for SNMPv1."
  ::= { mGuardSNMP 5 }

-- SNMP_COMMUNITY_RO
mGuardSNMPv1ROCommunity OBJECT-TYPE
  SYNTAX DisplayString
  ACCESS read-write
  STATUS mandatory
  DESCRIPTION
    "Variable name: SNMP_COMMUNITY_RO
    WebUi Label: Read-Only community
    Read-only community string for SNMPv1."
  ::= { mGuardSNMP 4 }

-- SNMP_ENABLE_V1
mGuardSNMPenableV1 OBJECT-TYPE
  SYNTAX INTEGER {
    yes(1),
    no(2)
  }
  ACCESS read-write
  STATUS mandatory
  DESCRIPTION
    "Variable name: SNMP_ENABLE_V1
    WebUi Label: Enable SNMPv1/v2 access
    Should SNMPv1 be enabled ?"
  ::= { mGuardSNMP 2 }

-- SNMP_ENABLE_V3
mGuardSNMPenableV3 OBJECT-TYPE
  SYNTAX INTEGER {
    yes(1),
    no(2)
  }
  ACCESS read-write
  STATUS mandatory
  DESCRIPTION
    "Variable name: SNMP_ENABLE_V3
    WebUi Label: Enable SNMPv3 access
    Should SNMPv3 be enabled ?"
  ::= { mGuardSNMP 1 }

-- SNMP_GAI_SECURITY_CONTEXT
mGuardSNMPGAISecurityContext OBJECT-TYPE
  SYNTAX INTEGER {
    admin(1),
    netadmin(2)
  }
  ACCESS read-write
  STATUS mandatory
  DESCRIPTION
    "Variable name: SNMP_GAI_SECURITY_CONTEXT
    WebUi Label: Run SNMP agent under the permissions of the following user
    GAI security context used to access/write configuration settings."
  ::= { mGuardSNMP 10 }

-- SNMP_LINKUPDOWN_TRAP
mGuardSNMPLinkUpDownTrapFlag OBJECT-TYPE
  SYNTAX INTEGER {
    yes(1),
    no(2)
  }
  ACCESS read-write
  STATUS mandatory
  DESCRIPTION
    "Variable name: SNMP_LINKUPDOWN_TRAP
    WebUi Label: Link up/down
    Link Up/Down Flag - Enable/Disable Link Up/Link Down traps for the
    entire security gateway."
  ::= { mGuardSNMPTrapConfigGroup 2 }

-- SNMP_LISTENPORT
mGuardSNMPport OBJECT-TYPE
  SYNTAX DisplayString
  ACCESS read-write
  STATUS mandatory
  DESCRIPTION
    "Variable name: SNMP_LISTENPORT
    WebUi Label: Port for incoming SNMP connections (remote access only)
    The port the SNMP agent listens to."
  ::= { mGuardSNMP 3 }

-- SNMP_TRAP_ADMIN_ACCESS
mGuardSNMPAdminAccessTrap OBJECT-TYPE
  SYNTAX INTEGER {
    yes(1),
    no(2)
  }
  ACCESS read-write
  STATUS mandatory
  DESCRIPTION
    "Variable name: SNMP_TRAP_ADMIN_ACCESS
    WebUi Label: Admin access (SSH, HTTPS)
    Enables/Disables traps on admin (SSH, HTTPS) login, logout or login
    tries."
  ::= { mGuardSNMPTrapConfigGroup 20 }

-- SNMP_TRAP_ADMIN_CONNECT
mGuardSNMPAdminConnectTrap OBJECT-TYPE
  SYNTAX INTEGER {
    yes(1),
    no(2)
  }
  ACCESS read-write
  STATUS mandatory
  DESCRIPTION
    "Variable name: SNMP_TRAP_ADMIN_CONNECT
    WebUi Label: Admin connection attempt (SSH, HTTPS)
    Enables/Disables traps on admin (SSH, HTTPS) connection attempts."
  ::= { mGuardSNMPTrapConfigGroup 19 }

-- SNMP_TRAP_AVDETECTION
mGuardSNMPAvDetectionTrapFlag OBJECT-TYPE
  SYNTAX INTEGER {
    yes(1),
    no(2)
  }
  ACCESS read-write
  STATUS mandatory
  DESCRIPTION
    "Variable name: SNMP_TRAP_AVDETECTION
    WebUi Label: Found a (suspicious) difference on a CIFS share
    Enables/Disables traps related virus detection events."
  ::= { mGuardSNMPTrapConfigGroup 16 }

-- SNMP_TRAP_AVFAIL
mGuardSNMPAvFailTrapFlag OBJECT-TYPE
  SYNTAX INTEGER {
    yes(1),
    no(2)
  }
  ACCESS read-write
  STATUS mandatory
  DESCRIPTION
    "Variable name: SNMP_TRAP_AVFAIL
    WebUi Label: Failed integrity check of a CIFS share
    Enables/Disables the traps with AntiVirus failures (update or engine
    failures)."
  ::= { mGuardSNMPTrapConfigGroup 7 }

-- SNMP_TRAP_AVINFO
mGuardSNMPAvInfoTrapFlag OBJECT-TYPE
  SYNTAX INTEGER {
    yes(1),
    no(2)
  }
  ACCESS read-write
  STATUS mandatory
  DESCRIPTION
    "Variable name: SNMP_TRAP_AVINFO
    WebUi Label: Successful integrity check of a CIFS share
    Enables/Disables the traps with informational AntiVirus messages."
  ::= { mGuardSNMPTrapConfigGroup 8 }

-- SNMP_TRAP_BLADECONFIG
mGuardSNMPBladeConfigTrapFlag OBJECT-TYPE
  SYNTAX INTEGER {
    yes(1),
    no(2)
  }
  ACCESS read-write
  STATUS mandatory
  DESCRIPTION
    "Variable name: SNMP_TRAP_BLADECONFIG
    WebUi Label: Blade reconfiguration (backup/restore)
    Enables/Disables traps sent at automatic blade configuration or
    backup."
  ::= { mGuardSNMPTrapConfigGroup 10 }

-- SNMP_TRAP_BLADESTATE
mGuardSNMPBladeStateTrapFlag OBJECT-TYPE
  SYNTAX INTEGER {
    yes(1),
    no(2)
  }
  ACCESS read-write
  STATUS mandatory
  DESCRIPTION
    "Variable name: SNMP_TRAP_BLADESTATE
    WebUi Label: Blade status change (replug, failure) and power supply
    Enables/Disables traps sent at blade status change."
  ::= { mGuardSNMPTrapConfigGroup 9 }

-- SNMP_TRAP_CMD
mGuardSNMPServiceInputTrapFlag OBJECT-TYPE
  SYNTAX INTEGER {
    yes(1),
    no(2)
  }
  ACCESS read-write
  STATUS mandatory
  DESCRIPTION
    "Variable name: SNMP_TRAP_CMD
    WebUi Label: Service input/CMD
    Enables/Disables traps sent on service input/CMD state changes."
  ::= { mGuardSNMPTrapConfigGroup 22 }

-- SNMP_TRAP_GSM
mGuardSNMPMobileNetworkTrapFlag OBJECT-TYPE
  SYNTAX INTEGER {
    yes(1),
    no(2)
  }
  ACCESS read-write
  STATUS mandatory
  DESCRIPTION
    "Variable name: SNMP_TRAP_GSM
    WebUi Label: Incoming text message and network supervision
    Enables/Disables traps related virus detection events."
  ::= { mGuardSNMPTrapConfigGroup 18 }

-- SNMP_TRAP_NEW_DHCP_CLIENT
mGuardSNMPNewDHCPClientTrap OBJECT-TYPE
  SYNTAX INTEGER {
    yes(1),
    no(2)
  }
  ACCESS read-write
  STATUS mandatory
  DESCRIPTION
    "Variable name: SNMP_TRAP_NEW_DHCP_CLIENT
    WebUi Label: New DHCP client
    Enables/Disables traps on new DHCP clients."
  ::= { mGuardSNMPTrapConfigGroup 21 }


-- SNMP_TRAP_RECEIVERS table
mGuardSNMPTrapReceiverTable OBJECT-TYPE
  SYNTAX SEQUENCE OF MGuardSNMPTrapReceiverEntry
  ACCESS not-accessible
  STATUS mandatory
  DESCRIPTION
    "A table of SNMP_TRAP_RECEIVERS"
  ::= { mGuardSNMP 7 }

-- SNMP_TRAP_RECEIVERS table entry
mGuardSNMPTrapReceiverEntry OBJECT-TYPE
  SYNTAX MGuardSNMPTrapReceiverEntry
  ACCESS not-accessible
  STATUS mandatory
  DESCRIPTION
    "An entry of SNMP_TRAP_RECEIVERS"
  INDEX { mGuardSNMPTrapReceiverIndex }
  ::= { mGuardSNMPTrapReceiverTable 1 }

MGuardSNMPTrapReceiverEntry ::= SEQUENCE {
  mGuardSNMPTrapReceiverIndex              INTEGER,
  mGuardSNMPTrapReceiverCommunity          DisplayString,
  mGuardSNMPTrapReceiverIPAddress          IpAddress,
  mGuardSNMPTrapReceiverName               DisplayString,
  mGuardSNMPTrapReceiverRowStatus          RowStatus,
  mGuardSNMPTrapReceiverPort               DisplayString
}

-- SNMP_TRAP_RECEIVERS table index
mGuardSNMPTrapReceiverIndex OBJECT-TYPE
  SYNTAX INTEGER (1..2147483647)
  ACCESS not-accessible
  STATUS mandatory
  DESCRIPTION
    "Index to SNMP_TRAP_RECEIVERS"
  ::= { mGuardSNMPTrapReceiverEntry 1 }

-- SNMP_TRAP_RECEIVERS row status
mGuardSNMPTrapReceiverRowStatus OBJECT-TYPE
  SYNTAX RowStatus
  ACCESS read-write
  STATUS mandatory
  DESCRIPTION
    "RowStatus of SNMP_TRAP_RECEIVERS"
  ::= { mGuardSNMPTrapReceiverEntry 5 }

-- SNMP_TRAP_RECEIVERS.TARGET_IP
mGuardSNMPTrapReceiverIPAddress OBJECT-TYPE
  SYNTAX IpAddress
  ACCESS read-write
  STATUS mandatory
  DESCRIPTION
    "Variable name: SNMP_TRAP_RECEIVERS.TARGET_IP
    WebUi Label: Destination IP
    IP Address - Each IP address parameter is four integer numbers. The
    numbers range from 0 to 255."
  ::= { mGuardSNMPTrapReceiverEntry 3 }

-- SNMP_TRAP_RECEIVERS.TARGET_NAME
mGuardSNMPTrapReceiverName OBJECT-TYPE
  SYNTAX DisplayString
  ACCESS read-write
  STATUS mandatory
  DESCRIPTION
    "Variable name: SNMP_TRAP_RECEIVERS.TARGET_NAME
    WebUi Label: Destination name
    The name of this Trap Receiver entry"
  ::= { mGuardSNMPTrapReceiverEntry 4 }

-- SNMP_TRAP_RECEIVERS.TARGET_PORT
mGuardSNMPTrapReceiverPort OBJECT-TYPE
  SYNTAX DisplayString
  ACCESS read-write
  STATUS mandatory
  DESCRIPTION
    "Variable name: SNMP_TRAP_RECEIVERS.TARGET_PORT
    WebUi Label: Destination port
    UDP Port (normally 162) to send trap to, service names allowed."
  ::= { mGuardSNMPTrapReceiverEntry 6 }

-- SNMP_TRAP_RECEIVERS.TARGET_COMMUNITY
mGuardSNMPTrapReceiverCommunity OBJECT-TYPE
  SYNTAX DisplayString
  ACCESS read-write
  STATUS mandatory
  DESCRIPTION
    "Variable name: SNMP_TRAP_RECEIVERS.TARGET_COMMUNITY
    WebUi Label: Destination community
    The security gateway's SNMP Trap Receiver Community Name. This is the
    SNMP community name of the remote network manager; the name can be up
    to 16 characters, and is case-sensitive."
  ::= { mGuardSNMPTrapReceiverEntry 2 }

-- SNMP_TRAP_REDUNDANCY_STATE
mGuardSNMPRouterHATrapFlag OBJECT-TYPE
  SYNTAX INTEGER {
    yes(1),
    no(2)
  }
  ACCESS read-write
  STATUS mandatory
  DESCRIPTION
    "Variable name: SNMP_TRAP_REDUNDANCY_STATE
    WebUi Label: Status change
    Enables/Disables traps sent at change of HA state."
  ::= { mGuardSNMPTrapConfigGroup 11 }

-- SNMP_TRAP_SECSTICK
mGuardSNMPSECStickTrap OBJECT-TYPE
  SYNTAX INTEGER {
    yes(1),
    no(2)
  }
  ACCESS read-write
  STATUS mandatory
  DESCRIPTION
    "Variable name: SNMP_TRAP_SECSTICK
    WebUi Label: SEC-Stick connection status changes
    Enables/Disables traps related to SEC-Stick connections."
  ::= { mGuardSNMPTrapConfigGroup 15 }

-- SNMP_TRAP_USER_FIREWALL
mGuardSNMPUserFirewallTrap OBJECT-TYPE
  SYNTAX INTEGER {
    yes(1),
    no(2)
  }
  ACCESS read-write
  STATUS mandatory
  DESCRIPTION
    "Variable name: SNMP_TRAP_USER_FIREWALL
    WebUi Label: User firewall traps
    Enables/Disables traps related to the user firewall."
  ::= { mGuardSNMPTrapConfigGroup 12 }

-- SNMP_TRAP_VPN_IPSEC
mGuardSNMPVPNIPsecConnStatusTrap OBJECT-TYPE
  SYNTAX INTEGER {
    yes(1),
    no(2)
  }
  ACCESS read-write
  STATUS mandatory
  DESCRIPTION
    "Variable name: SNMP_TRAP_VPN_IPSEC
    WebUi Label: IPsec connection status changes
    Enables/Disables traps related to the VPN IPsec connections."
  ::= { mGuardSNMPTrapConfigGroup 13 }

-- SNMP_TRAP_VPN_L2TP
mGuardSNMPVPNL2TPConnStatusTrap OBJECT-TYPE
  SYNTAX INTEGER {
    yes(1),
    no(2)
  }
  ACCESS read-write
  STATUS mandatory
  DESCRIPTION
    "Variable name: SNMP_TRAP_VPN_L2TP
    WebUi Label: L2TP connection status changes
    Enables/Disables traps related to the VPN L2TP connections."
  ::= { mGuardSNMPTrapConfigGroup 14 }

-- SNMP_V3_PASSWORD
mGuardSNMPv3Password OBJECT-TYPE
  SYNTAX DisplayString
  ACCESS read-write
  STATUS mandatory
  DESCRIPTION
    "Variable name: SNMP_V3_PASSWORD
    WebUi Label: Password
    SNMPv3 password."
  ::= { mGuardSNMP 13 }

-- SNMP_V3_USERNAME
mGuardSNMPv3Username OBJECT-TYPE
  SYNTAX DisplayString
  ACCESS read-write
  STATUS mandatory
  DESCRIPTION
    "Variable name: SNMP_V3_USERNAME
    WebUi Label: User name
    SNMPv3 user name."
  ::= { mGuardSNMP 12 }

-- SSH_ADMIN_LOGIN_ALLOWED_MAX
mGuardSSHAdminLoginMax OBJECT-TYPE
  SYNTAX INTEGER(2..2147483647)
  ACCESS read-write
  STATUS mandatory
  DESCRIPTION
    "Variable name: SSH_ADMIN_LOGIN_ALLOWED_MAX
    WebUi Label: Admin
    Sets the maximum number of allowed concurrent authenticated and active
    'admin' SSH sessions. The SSH daemon may allow additional not yet
    authenticated sessions."
  ::= { mGuardSSHRemoteAccess 10 }

-- SSH_AUDIT_LOGIN_ALLOWED_MAX
mGuardSSHAuditLoginMax OBJECT-TYPE
  SYNTAX INTEGER
  ACCESS read-write
  STATUS mandatory
  DESCRIPTION
    "Variable name: SSH_AUDIT_LOGIN_ALLOWED_MAX
    WebUi Label: Audit
    Sets the maximum number of allowed concurrent authenticated and active
    'audit' SSH sessions. The SSH daemon may allow additional not yet
    authenticated sessions."
  ::= { mGuardSSHRemoteAccess 12 }


-- SSH_CA_CERTS table
mGuardSSHX509CARefsTable OBJECT-TYPE
  SYNTAX SEQUENCE OF MGuardSSHX509CARefsEntry
  ACCESS not-accessible
  STATUS mandatory
  DESCRIPTION
    "A table of SSH_CA_CERTS"
  ::= { mGuardSSHX509 4 }

-- SSH_CA_CERTS table entry
mGuardSSHX509CARefsEntry OBJECT-TYPE
  SYNTAX MGuardSSHX509CARefsEntry
  ACCESS not-accessible
  STATUS mandatory
  DESCRIPTION
    "An entry of SSH_CA_CERTS"
  INDEX { mGuardSSHX509CARefsIdx }
  ::= { mGuardSSHX509CARefsTable 1 }

MGuardSSHX509CARefsEntry ::= SEQUENCE {
  mGuardSSHX509CARefsIdx                   INTEGER,
  mGuardSSHX509CARefsRowStatus             RowStatus,
  mGuardSSHX509CARefsNewRef                OBJECT IDENTIFIER
}

-- SSH_CA_CERTS table index
mGuardSSHX509CARefsIdx OBJECT-TYPE
  SYNTAX INTEGER (1..2147483647)
  ACCESS not-accessible
  STATUS mandatory
  DESCRIPTION
    "Index to SSH_CA_CERTS"
  ::= { mGuardSSHX509CARefsEntry 1 }

-- SSH_CA_CERTS row status
mGuardSSHX509CARefsRowStatus OBJECT-TYPE
  SYNTAX RowStatus
  ACCESS read-write
  STATUS mandatory
  DESCRIPTION
    "RowStatus of SSH_CA_CERTS"
  ::= { mGuardSSHX509CARefsEntry 10 }

-- SSH_CA_CERTS.CERTIFICATE_REF reference
mGuardSSHX509CARefsNewRef OBJECT-TYPE
  SYNTAX OBJECT IDENTIFIER
  ACCESS read-write
  STATUS mandatory
  DESCRIPTION
    "Variable name: SSH_CA_CERTS.CERTIFICATE_REF
    WebUi Label: CA certificate
    When this object contains the OID of an 'mGuardCertsCAIndex' object,
    the corresponding CA certificate is used to validate the remote peer."
  ::= { mGuardSSHX509CARefsEntry 11 }

-- SSH_CLIENT_ALIVE_COUNT_MAX
mGuardSSHClientAliveMaxC OBJECT-TYPE
  SYNTAX INTEGER(1..10)
  ACCESS read-write
  STATUS mandatory
  DESCRIPTION
    "Variable name: SSH_CLIENT_ALIVE_COUNT_MAX
    WebUi Label: Maximum number of missing signs of life
    Sets the number of client alive messages (see
    mGuardSSHClientAliveSecs) which may be sent without the mGuard
    receiving any messages back from the client. If this threshold is
    reached while client alive messages are being sent, the mGuard will
    disconnect the client, terminating the session."
  ::= { mGuardSSHRemoteAccess 9 }

-- SSH_CLIENT_ALIVE_INTERVAL_SECS
mGuardSSHClientAliveSecs OBJECT-TYPE
  SYNTAX INTEGER(0..3600)
  ACCESS read-write
  STATUS mandatory
  DESCRIPTION
    "Variable name: SSH_CLIENT_ALIVE_INTERVAL_SECS
    WebUi Label: Delay between requests for a sign of life (The value 0 indicates that
     these messages will not be sent.)
    Sets a timeout interval in seconds after which if no data has been
    received from the client, the SSH server will send a message through
    the encrypted channel to request a response from the client. The
    default is 0, indicating that these messages will not be sent to the
    client. This object (having a default value of 120s) replaces the now
    deprecated mGuardSSHClientAliveSeconds object which had the default 0."
  ::= { mGuardSSHRemoteAccess 13 }

-- SSH_MGUARD_SECURE_CLOUD_ENABLE
mGuardSSHSecCloudAdminEnable OBJECT-TYPE
  SYNTAX INTEGER {
    yes(1),
    no(2)
  }
  ACCESS read-write
  STATUS mandatory
  DESCRIPTION
    "Variable name: SSH_MGUARD_SECURE_CLOUD_ENABLE
    WebUi Label: SSH remote access for mGuard Secure Cloud private via IPsec
    Value on field device to allow remote access from a Secure Cloud
    routing engine via VPN tunnel: yes: enabled no: disabled"
  ::= { mGuardSSHRemoteAccess 14 }

-- SSH_MOBILE_LOGIN_ALLOWED_MAX
mGuardSSHMobileLoginMax OBJECT-TYPE
  SYNTAX INTEGER
  ACCESS read-write
  STATUS mandatory
  DESCRIPTION
    "Variable name: SSH_MOBILE_LOGIN_ALLOWED_MAX
    WebUi Label: Mobile
    Sets the maximum number of allowed concurrent authenticated and active
    'mobile' SSH sessions. The SSH daemon may allow additional not yet
    authenticated sessions."
  ::= { mGuardSSHRemoteAccess 15 }

-- SSH_NETADMIN_LOGIN_ALLOWED_MAX
mGuardSSHNetadminLoginMax OBJECT-TYPE
  SYNTAX INTEGER
  ACCESS read-write
  STATUS mandatory
  DESCRIPTION
    "Variable name: SSH_NETADMIN_LOGIN_ALLOWED_MAX
    WebUi Label: Netadmin
    Sets the maximum number of allowed concurrent authenticated and active
    'netadmin' SSH sessions. The SSH daemon may allow additional not yet
    authenticated sessions."
  ::= { mGuardSSHRemoteAccess 11 }

-- SSH_REMOTE_ACCESS_RULES
mGuardSSHRemoteUUID OBJECT-TYPE
  SYNTAX DisplayString
  ACCESS read-only
  STATUS mandatory
  DESCRIPTION
    "Variable name: SSH_REMOTE_ACCESS_RULES
    WebUi Label: Allowed networks
    Universally Unique Identifier (UUID, RFC 4122) used for
    mGuardSSHRemoteFWRuleTable logging."
  ::= { mGuardSSHRemoteAccess 4 }


-- SSH_REMOTE_ACCESS_RULES table
mGuardSSHRemoteFWRuleTable OBJECT-TYPE
  SYNTAX SEQUENCE OF MGuardSSHRemoteFWRuleEntry
  ACCESS not-accessible
  STATUS mandatory
  DESCRIPTION
    "A table of SSH_REMOTE_ACCESS_RULES"
  ::= { mGuardSSHRemoteAccess 3 }

-- SSH_REMOTE_ACCESS_RULES table entry
mGuardSSHRemoteFWRuleEntry OBJECT-TYPE
  SYNTAX MGuardSSHRemoteFWRuleEntry
  ACCESS not-accessible
  STATUS mandatory
  DESCRIPTION
    "An entry of SSH_REMOTE_ACCESS_RULES"
  INDEX { mGuardSSHFWruleIndex }
  ::= { mGuardSSHRemoteFWRuleTable 1 }

MGuardSSHRemoteFWRuleEntry ::= SEQUENCE {
  mGuardSSHFWruleIndex                     INTEGER,
  mGuardSSHFWsourceIP                      DisplayString,
  mGuardSSHFWinterface                     INTEGER,
  mGuardSSHFWtarget                        INTEGER,
  mGuardSSHFWlog                           INTEGER,
  mGuardSSHFWRowStatus                     RowStatus,
  mGuardSSHFWcomment                       DisplayString,
  mGuardSSHFWfromMAC                       MacAddress
}

-- SSH_REMOTE_ACCESS_RULES table index
mGuardSSHFWruleIndex OBJECT-TYPE
  SYNTAX INTEGER (1..2147483647)
  ACCESS not-accessible
  STATUS mandatory
  DESCRIPTION
    "Index to SSH_REMOTE_ACCESS_RULES"
  ::= { mGuardSSHRemoteFWRuleEntry 1 }

-- SSH_REMOTE_ACCESS_RULES row status
mGuardSSHFWRowStatus OBJECT-TYPE
  SYNTAX RowStatus
  ACCESS read-write
  STATUS mandatory
  DESCRIPTION
    "RowStatus of SSH_REMOTE_ACCESS_RULES"
  ::= { mGuardSSHRemoteFWRuleEntry 6 }

-- SSH_REMOTE_ACCESS_RULES.COMMENT
mGuardSSHFWcomment OBJECT-TYPE
  SYNTAX DisplayString
  ACCESS read-write
  STATUS mandatory
  DESCRIPTION
    "Variable name: SSH_REMOTE_ACCESS_RULES.COMMENT
    WebUi Label: Comment
    Commentary or name for this rule."
  ::= { mGuardSSHRemoteFWRuleEntry 7 }

-- SSH_REMOTE_ACCESS_RULES.LOG
mGuardSSHFWlog OBJECT-TYPE
  SYNTAX INTEGER {
    yes(1),
    no(2)
  }
  ACCESS read-write
  STATUS mandatory
  DESCRIPTION
    "Variable name: SSH_REMOTE_ACCESS_RULES.LOG
    WebUi Label: Log
    Log packets matching this rule ?"
  ::= { mGuardSSHRemoteFWRuleEntry 5 }

-- SSH_REMOTE_ACCESS_RULES.FROM_IP
mGuardSSHFWsourceIP OBJECT-TYPE
  SYNTAX DisplayString
  ACCESS read-write
  STATUS mandatory
  DESCRIPTION
    "Variable name: SSH_REMOTE_ACCESS_RULES.FROM_IP
    WebUi Label: From IP
    The rule's source IP address"
  ::= { mGuardSSHRemoteFWRuleEntry 2 }

-- SSH_REMOTE_ACCESS_RULES.INTERFACE_DEV
mGuardSSHFWinterface OBJECT-TYPE
  SYNTAX INTEGER {
    extern(1),
    intern(2),
    extern2(3),
    dialin(4),
    viaipsec(5),
    dmz0(6),
    viagre(7)
  }
  ACCESS read-write
  STATUS mandatory
  DESCRIPTION
    "Variable name: SSH_REMOTE_ACCESS_RULES.INTERFACE_DEV
    WebUi Label: Interface
    The network interface the rule belongs to (extern/intern/dmz)."
  ::= { mGuardSSHRemoteFWRuleEntry 3 }

-- SSH_REMOTE_ACCESS_RULES.FROM_MAC
mGuardSSHFWfromMAC OBJECT-TYPE
  SYNTAX MacAddress
  ACCESS read-write
  STATUS mandatory
  DESCRIPTION
    "Variable name: SSH_REMOTE_ACCESS_RULES.FROM_MAC
    WebUi Label: From MAC
    The rule's source MAC address."
  ::= { mGuardSSHRemoteFWRuleEntry 8 }

-- SSH_REMOTE_ACCESS_RULES.TARGET
mGuardSSHFWtarget OBJECT-TYPE
  SYNTAX INTEGER {
    accept(1),
    reject(2),
    drop(3)
  }
  ACCESS read-write
  STATUS mandatory
  DESCRIPTION
    "Variable name: SSH_REMOTE_ACCESS_RULES.TARGET
    WebUi Label: Action
    The target of the rule (accept/reject/drop)."
  ::= { mGuardSSHRemoteFWRuleEntry 4 }

-- SSH_REMOTE_ENABLE
mGuardSSHRemoteEnable OBJECT-TYPE
  SYNTAX INTEGER {
    yes(1),
    no(2)
  }
  ACCESS read-write
  STATUS mandatory
  DESCRIPTION
    "Variable name: SSH_REMOTE_ENABLE
    WebUi Label: Enable SSH remote access
    Value to control SSH remote access: yes: enabled no: disabled"
  ::= { mGuardSSHRemoteAccess 1 }

-- SSH_REMOTE_LISTENPORT
mGuardSSHRemotePort OBJECT-TYPE
  SYNTAX DisplayString
  ACCESS read-write
  STATUS mandatory
  DESCRIPTION
    "Variable name: SSH_REMOTE_LISTENPORT
    WebUi Label: Port for incoming SSH connections (remote administration only)
    Port for SSH remote Access (regularly 22), service names allowed."
  ::= { mGuardSSHRemoteAccess 2 }

-- SSH_ROOT_LOGIN_ENABLE
mGuardSSHRootLoginEnable OBJECT-TYPE
  SYNTAX INTEGER {
    yes(1),
    no(2)
  }
  ACCESS read-write
  STATUS mandatory
  DESCRIPTION
    "Variable name: SSH_ROOT_LOGIN_ENABLE
    WebUi Label: Allow SSH login as user root
    Allow SSH login as user root"
  ::= { mGuardSSHRemoteAccess 16 }

-- SSH_SERVER_CERT_REF
mGuardSSHX509LocalCertValue OBJECT-TYPE
  SYNTAX INTEGER {
    none(1)
  }
  ACCESS read-write
  STATUS mandatory
  DESCRIPTION
    "Variable name: SSH_SERVER_CERT_REF
    WebUi Label: SSH server certificate
    This object is effective if and only if the
    'mGuardSSHX509LocalCertRef' object contains the OID of this object.
    When this object is read, it always returns the value 'none'. When the
    value 'none' is written to this object, no local machine certificate
    is used."
  ::= { mGuardSSHX509 7 }

-- SSH_SERVER_CERT_REF reference
mGuardSSHX509LocalCertRef OBJECT-TYPE
  SYNTAX OBJECT IDENTIFIER
  ACCESS read-write
  STATUS mandatory
  DESCRIPTION
    "Variable name: SSH_SERVER_CERT_REF
    WebUi Label: SSH server certificate
    When this object contains the OID of an 'mGuardCertsLocalIndex'
    object, the corresponding X.509 certificate and private key is used to
    identify this site. To select a local machine certificate in this
    manner, write the OID of the corresponding 'mGuardCertsLocalIndex'
    object to this object. To disable this feature, set the
    'mGuardSSHX509LocalCertValue' object."
  ::= { mGuardSSHX509 8 }


-- SSH_X509_AUTH table
mGuardSSHX509AuthSubjTable OBJECT-TYPE
  SYNTAX SEQUENCE OF MGuardSSHX509AuthSubjEntry
  ACCESS not-accessible
  STATUS mandatory
  DESCRIPTION
    "A table of SSH_X509_AUTH"
  ::= { mGuardSSHX509 5 }

-- SSH_X509_AUTH table entry
mGuardSSHX509AuthSubjEntry OBJECT-TYPE
  SYNTAX MGuardSSHX509AuthSubjEntry
  ACCESS not-accessible
  STATUS mandatory
  DESCRIPTION
    "An entry of SSH_X509_AUTH"
  INDEX { mGuardSSHX509AuthSubjIdx }
  ::= { mGuardSSHX509AuthSubjTable 1 }

MGuardSSHX509AuthSubjEntry ::= SEQUENCE {
  mGuardSSHX509AuthSubjIdx                 INTEGER,
  mGuardSSHX509AuthSubjSubject             DisplayString,
  mGuardSSHX509AuthSubjUser                INTEGER,
  mGuardSSHX509AuthSubjRowStatus           RowStatus
}

-- SSH_X509_AUTH table index
mGuardSSHX509AuthSubjIdx OBJECT-TYPE
  SYNTAX INTEGER (1..2147483647)
  ACCESS not-accessible
  STATUS mandatory
  DESCRIPTION
    "Index to SSH_X509_AUTH"
  ::= { mGuardSSHX509AuthSubjEntry 1 }

-- SSH_X509_AUTH row status
mGuardSSHX509AuthSubjRowStatus OBJECT-TYPE
  SYNTAX RowStatus
  ACCESS read-write
  STATUS mandatory
  DESCRIPTION
    "RowStatus of SSH_X509_AUTH"
  ::= { mGuardSSHX509AuthSubjEntry 10 }

-- SSH_X509_AUTH.USER
mGuardSSHX509AuthSubjUser OBJECT-TYPE
  SYNTAX INTEGER {
    all(1),
    root(2),
    admin(3),
    netadmin(4),
    audit(5),
    mobile(6)
  }
  ACCESS read-write
  STATUS mandatory
  DESCRIPTION
    "Variable name: SSH_X509_AUTH.USER
    WebUi Label: Authorized for access as
    The user authenticated by the X.509 certificate."
  ::= { mGuardSSHX509AuthSubjEntry 3 }

-- SSH_X509_AUTH.SUBJECT
mGuardSSHX509AuthSubjSubject OBJECT-TYPE
  SYNTAX DisplayString
  ACCESS read-write
  STATUS mandatory
  DESCRIPTION
    "Variable name: SSH_X509_AUTH.SUBJECT
    WebUi Label: X.509 subject
    The X.509 subject that needs to be included in certificate."
  ::= { mGuardSSHX509AuthSubjEntry 2 }


-- SSH_X509_AUTH_BLOB table
mGuardSSHX509AuthCertTable OBJECT-TYPE
  SYNTAX SEQUENCE OF MGuardSSHX509AuthCertEntry
  ACCESS not-accessible
  STATUS mandatory
  DESCRIPTION
    "A table of SSH_X509_AUTH_BLOB"
  ::= { mGuardSSHX509 6 }

-- SSH_X509_AUTH_BLOB table entry
mGuardSSHX509AuthCertEntry OBJECT-TYPE
  SYNTAX MGuardSSHX509AuthCertEntry
  ACCESS not-accessible
  STATUS mandatory
  DESCRIPTION
    "An entry of SSH_X509_AUTH_BLOB"
  INDEX { mGuardSSHX509AuthCertIdx }
  ::= { mGuardSSHX509AuthCertTable 1 }

MGuardSSHX509AuthCertEntry ::= SEQUENCE {
  mGuardSSHX509AuthCertIdx                 INTEGER,
  mGuardSSHX509AuthCertUsr                 INTEGER,
  mGuardSSHX509AuthCertRowStatus           RowStatus,
  mGuardSSHX509AuthCertNewRef              OBJECT IDENTIFIER
}

-- SSH_X509_AUTH_BLOB table index
mGuardSSHX509AuthCertIdx OBJECT-TYPE
  SYNTAX INTEGER (1..2147483647)
  ACCESS not-accessible
  STATUS mandatory
  DESCRIPTION
    "Index to SSH_X509_AUTH_BLOB"
  ::= { mGuardSSHX509AuthCertEntry 1 }

-- SSH_X509_AUTH_BLOB row status
mGuardSSHX509AuthCertRowStatus OBJECT-TYPE
  SYNTAX RowStatus
  ACCESS read-write
  STATUS mandatory
  DESCRIPTION
    "RowStatus of SSH_X509_AUTH_BLOB"
  ::= { mGuardSSHX509AuthCertEntry 10 }

-- SSH_X509_AUTH_BLOB.CERTIFICATE_REF reference
mGuardSSHX509AuthCertNewRef OBJECT-TYPE
  SYNTAX OBJECT IDENTIFIER
  ACCESS read-write
  STATUS mandatory
  DESCRIPTION
    "Variable name: SSH_X509_AUTH_BLOB.CERTIFICATE_REF
    WebUi Label: Client certificate
    When this object contains the OID of an 'mGuardCertsRemoteIndex'
    object, the corresponding remote certificate is used for the SSH X.509
    authentication."
  ::= { mGuardSSHX509AuthCertEntry 11 }

-- SSH_X509_AUTH_BLOB.USER
mGuardSSHX509AuthCertUsr OBJECT-TYPE
  SYNTAX INTEGER {
    all(1),
    root(2),
    admin(3),
    netadmin(4),
    audit(5),
    mobile(6)
  }
  ACCESS read-write
  STATUS mandatory
  DESCRIPTION
    "Variable name: SSH_X509_AUTH_BLOB.USER
    WebUi Label: Authorized for access as
    The user authenticated by the X.509 certificate."
  ::= { mGuardSSHX509AuthCertEntry 3 }

-- SSH_X509_ENABLE
mGuardSSHX509Enable OBJECT-TYPE
  SYNTAX INTEGER {
    yes(1),
    no(2)
  }
  ACCESS read-write
  STATUS mandatory
  DESCRIPTION
    "Variable name: SSH_X509_ENABLE
    WebUi Label: Enable X.509 certificates for SSH access
    Enable additional X.509 certificate authentication?"
  ::= { mGuardSSHX509 1 }


-- STATIC_MULTICAST_GROUP table
mGuardStaticMulticastTable OBJECT-TYPE
  SYNTAX SEQUENCE OF MGuardStaticMulticastEntry
  ACCESS not-accessible
  STATUS mandatory
  DESCRIPTION
    "A table of STATIC_MULTICAST_GROUP"
  ::= { mGuardStaticMulticast 1 }

-- STATIC_MULTICAST_GROUP table entry
mGuardStaticMulticastEntry OBJECT-TYPE
  SYNTAX MGuardStaticMulticastEntry
  ACCESS not-accessible
  STATUS mandatory
  DESCRIPTION
    "An entry of STATIC_MULTICAST_GROUP"
  INDEX { mGuardStaticMulticastIndex }
  ::= { mGuardStaticMulticastTable 1 }

MGuardStaticMulticastEntry ::= SEQUENCE {
  mGuardStaticMulticastIndex               INTEGER,
  mGuardStaticMulticastRowStatus           RowStatus,
  mGuardStaticMulticastMac                 MacAddress,
  mGuardStaticMulticastPort0               INTEGER,
  mGuardStaticMulticastPort1               INTEGER,
  mGuardStaticMulticastPort2               INTEGER,
  mGuardStaticMulticastPort3               INTEGER,
  mGuardStaticMulticastPort4               INTEGER,
  mGuardStaticMulticastInternal            INTEGER
}

-- STATIC_MULTICAST_GROUP table index
mGuardStaticMulticastIndex OBJECT-TYPE
  SYNTAX INTEGER (1..2147483647)
  ACCESS not-accessible
  STATUS mandatory
  DESCRIPTION
    "Index to STATIC_MULTICAST_GROUP"
  ::= { mGuardStaticMulticastEntry 1 }

-- STATIC_MULTICAST_GROUP row status
mGuardStaticMulticastRowStatus OBJECT-TYPE
  SYNTAX RowStatus
  ACCESS read-write
  STATUS mandatory
  DESCRIPTION
    "RowStatus of STATIC_MULTICAST_GROUP"
  ::= { mGuardStaticMulticastEntry 2 }

-- STATIC_MULTICAST_GROUP.MAC
mGuardStaticMulticastMac OBJECT-TYPE
  SYNTAX MacAddress
  ACCESS read-write
  STATUS mandatory
  DESCRIPTION
    "Variable name: STATIC_MULTICAST_GROUP.MAC
    WebUi Label: Multicast group address
    The MAC address for a static multicast group"
  ::= { mGuardStaticMulticastEntry 3 }

-- STATIC_MULTICAST_GROUP.INTERNAL
mGuardStaticMulticastInternal OBJECT-TYPE
  SYNTAX INTEGER {
    yes(1),
    no(2)
  }
  ACCESS read-write
  STATUS mandatory
  DESCRIPTION
    "Variable name: STATIC_MULTICAST_GROUP.INTERNAL
    WebUi Label: WAN
    Set whether the mGuard-internal port of the switch is in this static
    multicast group"
  ::= { mGuardStaticMulticastEntry 9 }

-- STATIC_MULTICAST_GROUP.PORT4
mGuardStaticMulticastPort4 OBJECT-TYPE
  SYNTAX INTEGER {
    yes(1),
    no(2)
  }
  ACCESS read-write
  STATUS mandatory
  DESCRIPTION
    "Variable name: STATIC_MULTICAST_GROUP.PORT4
    WebUi Label: LAN5
    Set whether phy #4 is in this static multicast group"
  ::= { mGuardStaticMulticastEntry 8 }

-- STATIC_MULTICAST_GROUP.PORT2
mGuardStaticMulticastPort2 OBJECT-TYPE
  SYNTAX INTEGER {
    yes(1),
    no(2)
  }
  ACCESS read-write
  STATUS mandatory
  DESCRIPTION
    "Variable name: STATIC_MULTICAST_GROUP.PORT2
    WebUi Label: LAN1
    Set whether phy #2 is in this static multicast group"
  ::= { mGuardStaticMulticastEntry 6 }

-- STATIC_MULTICAST_GROUP.PORT3
mGuardStaticMulticastPort3 OBJECT-TYPE
  SYNTAX INTEGER {
    yes(1),
    no(2)
  }
  ACCESS read-write
  STATUS mandatory
  DESCRIPTION
    "Variable name: STATIC_MULTICAST_GROUP.PORT3
    WebUi Label: LAN4
    Set whether phy #3 is in this static multicast group"
  ::= { mGuardStaticMulticastEntry 7 }

-- STATIC_MULTICAST_GROUP.PORT0
mGuardStaticMulticastPort0 OBJECT-TYPE
  SYNTAX INTEGER {
    yes(1),
    no(2)
  }
  ACCESS read-write
  STATUS mandatory
  DESCRIPTION
    "Variable name: STATIC_MULTICAST_GROUP.PORT0
    WebUi Label: LAN2
    Set whether phy #0 is in this static multicast group"
  ::= { mGuardStaticMulticastEntry 4 }

-- STATIC_MULTICAST_GROUP.PORT1
mGuardStaticMulticastPort1 OBJECT-TYPE
  SYNTAX INTEGER {
    yes(1),
    no(2)
  }
  ACCESS read-write
  STATUS mandatory
  DESCRIPTION
    "Variable name: STATIC_MULTICAST_GROUP.PORT1
    WebUi Label: LAN3
    Set whether phy #1 is in this static multicast group"
  ::= { mGuardStaticMulticastEntry 5 }


-- STEALTH_ALT_ROUTES table
mGuardStealthManageAltRouteTable OBJECT-TYPE
  SYNTAX SEQUENCE OF MGuardStealthManageAltRouteEntry
  ACCESS not-accessible
  STATUS mandatory
  DESCRIPTION
    "A table of STEALTH_ALT_ROUTES"
  ::= { mGuardStealthInterface 6 }

-- STEALTH_ALT_ROUTES table entry
mGuardStealthManageAltRouteEntry OBJECT-TYPE
  SYNTAX MGuardStealthManageAltRouteEntry
  ACCESS not-accessible
  STATUS mandatory
  DESCRIPTION
    "An entry of STEALTH_ALT_ROUTES"
  INDEX { mGuardStealthManageAltRouteIndex }
  ::= { mGuardStealthManageAltRouteTable 1 }

MGuardStealthManageAltRouteEntry ::= SEQUENCE {
  mGuardStealthManageAltRouteIndex         INTEGER,
  mGuardStealthManageAltRouteNet           DisplayString,
  mGuardStealthManageAltRouteGW            IpAddress,
  mGuardStealthManageAltRouteRowSt         RowStatus
}

-- STEALTH_ALT_ROUTES table index
mGuardStealthManageAltRouteIndex OBJECT-TYPE
  SYNTAX INTEGER (1..2147483647)
  ACCESS not-accessible
  STATUS mandatory
  DESCRIPTION
    "Index to STEALTH_ALT_ROUTES"
  ::= { mGuardStealthManageAltRouteEntry 1 }

-- STEALTH_ALT_ROUTES row status
mGuardStealthManageAltRouteRowSt OBJECT-TYPE
  SYNTAX RowStatus
  ACCESS read-write
  STATUS mandatory
  DESCRIPTION
    "RowStatus of STEALTH_ALT_ROUTES"
  ::= { mGuardStealthManageAltRouteEntry 10 }

-- STEALTH_ALT_ROUTES.GATEWAY
mGuardStealthManageAltRouteGW OBJECT-TYPE
  SYNTAX IpAddress
  ACCESS read-write
  STATUS mandatory
  DESCRIPTION
    "Variable name: STEALTH_ALT_ROUTES.GATEWAY
    WebUi Label: Gateway
    Alternative gateway to be used for the network."
  ::= { mGuardStealthManageAltRouteEntry 3 }

-- STEALTH_ALT_ROUTES.NETWORK
mGuardStealthManageAltRouteNet OBJECT-TYPE
  SYNTAX DisplayString
  ACCESS read-write
  STATUS mandatory
  DESCRIPTION
    "Variable name: STEALTH_ALT_ROUTES.NETWORK
    WebUi Label: Network
    Network to be routed over an alternative gateway."
  ::= { mGuardStealthManageAltRouteEntry 2 }

-- STEALTH_AUTO_IGNORE_TCP139
mGuardStealthAutoDetectIgnTCP139 OBJECT-TYPE
  SYNTAX INTEGER {
    yes(1),
    no(2)
  }
  ACCESS read-write
  STATUS mandatory
  DESCRIPTION
    "Variable name: STEALTH_AUTO_IGNORE_TCP139
    WebUi Label: Autodetect: ignore NetBIOS over TCP traffic on TCP port 139
    Ignore traffic from/to TCP port 139 (NetBIOS over TCP) during
    automatic network configuration."
  ::= { mGuardStealthIPConfAutoDetect 1 }

-- STEALTH_ENABLE_DHCP_FORWARDING
mGuardStealthL2ForwardDHCP OBJECT-TYPE
  SYNTAX INTEGER {
    yes(1),
    no(2)
  }
  ACCESS read-write
  STATUS mandatory
  DESCRIPTION
    "Variable name: STEALTH_ENABLE_DHCP_FORWARDING
    WebUi Label: Allow forwarding of DHCP frames
    Enable DHCP forwarding in Stealth Mode. This will allow computers on
    the internal/protected side to receive their configuration via DHCP
    even if no special DHCP rule is configured in the firewall"
  ::= { mGuardStealthL2Filter 5 }

-- STEALTH_ENABLE_GVRP_FORWARDING
mGuardStealthL2ForwardGVRP OBJECT-TYPE
  SYNTAX INTEGER {
    yes(1),
    no(2)
  }
  ACCESS read-write
  STATUS mandatory
  DESCRIPTION
    "Variable name: STEALTH_ENABLE_GVRP_FORWARDING
    WebUi Label: Allow forwarding of GVRP frames
    Enable GVRP forwarding in Stealth Mode."
  ::= { mGuardStealthL2Filter 3 }

-- STEALTH_ENABLE_STP_FORWARDING
mGuardStealthL2ForwardSTP OBJECT-TYPE
  SYNTAX INTEGER {
    yes(1),
    no(2)
  }
  ACCESS read-write
  STATUS mandatory
  DESCRIPTION
    "Variable name: STEALTH_ENABLE_STP_FORWARDING
    WebUi Label: Allow forwarding of STP frames
    Enable STP forwarding in Stealth Mode."
  ::= { mGuardStealthL2Filter 4 }

-- STEALTH_IP
mGuardStealthStaticIP OBJECT-TYPE
  SYNTAX IpAddress
  ACCESS read-write
  STATUS mandatory
  DESCRIPTION
    "Variable name: STEALTH_IP
    WebUi Label: Client's IP address
    IP address of the protected client in stealth mode (using static IP
    configuration)."
  ::= { mGuardStealthIPConfStatic 1 }


-- STEALTH_L2_FILTER_EXTERN table
mGuardL2FilterExternTable OBJECT-TYPE
  SYNTAX SEQUENCE OF MGuardL2FilterExternEntry
  ACCESS not-accessible
  STATUS mandatory
  DESCRIPTION
    "A table of STEALTH_L2_FILTER_EXTERN"
  ::= { mGuardStealthL2Filter 2 }

-- STEALTH_L2_FILTER_EXTERN table entry
mGuardL2FilterExternEntry OBJECT-TYPE
  SYNTAX MGuardL2FilterExternEntry
  ACCESS not-accessible
  STATUS mandatory
  DESCRIPTION
    "An entry of STEALTH_L2_FILTER_EXTERN"
  INDEX { mGuardL2FilterExternRuleIndex }
  ::= { mGuardL2FilterExternTable 1 }

MGuardL2FilterExternEntry ::= SEQUENCE {
  mGuardL2FilterExternRuleIndex            INTEGER,
  mGuardL2FilterExternRowStatus            RowStatus,
  mGuardL2FilterExternTarget               INTEGER,
  mGuardL2FilterExternComment              DisplayString,
  mGuardL2FilterExternSrcMacWld            DisplayString,
  mGuardL2FilterExternDstMacWld            DisplayString,
  mGuardL2FilterExternEthProto             DisplayString
}

-- STEALTH_L2_FILTER_EXTERN table index
mGuardL2FilterExternRuleIndex OBJECT-TYPE
  SYNTAX INTEGER (1..2147483647)
  ACCESS not-accessible
  STATUS mandatory
  DESCRIPTION
    "Index to STEALTH_L2_FILTER_EXTERN"
  ::= { mGuardL2FilterExternEntry 1 }

-- STEALTH_L2_FILTER_EXTERN row status
mGuardL2FilterExternRowStatus OBJECT-TYPE
  SYNTAX RowStatus
  ACCESS read-write
  STATUS mandatory
  DESCRIPTION
    "RowStatus of STEALTH_L2_FILTER_EXTERN"
  ::= { mGuardL2FilterExternEntry 2 }

-- STEALTH_L2_FILTER_EXTERN.COMMENT
mGuardL2FilterExternComment OBJECT-TYPE
  SYNTAX DisplayString
  ACCESS read-write
  STATUS mandatory
  DESCRIPTION
    "Variable name: STEALTH_L2_FILTER_EXTERN.COMMENT
    WebUi Label: Comment
    Comment or name for this rule."
  ::= { mGuardL2FilterExternEntry 7 }

-- STEALTH_L2_FILTER_EXTERN.SOURCE_MAC
mGuardL2FilterExternSrcMacWld OBJECT-TYPE
  SYNTAX DisplayString
  ACCESS read-write
  STATUS mandatory
  DESCRIPTION
    "Variable name: STEALTH_L2_FILTER_EXTERN.SOURCE_MAC
    WebUi Label: Source MAC
    Source MAC Address to apply this filter rule for. The special string
    'xx' for an octet matches any value."
  ::= { mGuardL2FilterExternEntry 8 }

-- STEALTH_L2_FILTER_EXTERN.ETHERTYPE_HEX
mGuardL2FilterExternEthProto OBJECT-TYPE
  SYNTAX DisplayString
  ACCESS read-write
  STATUS mandatory
  DESCRIPTION
    "Variable name: STEALTH_L2_FILTER_EXTERN.ETHERTYPE_HEX
    WebUi Label: Ethernet protocol
    Ethernet type to apply this filter rule for."
  ::= { mGuardL2FilterExternEntry 10 }

-- STEALTH_L2_FILTER_EXTERN.DEST_MAC
mGuardL2FilterExternDstMacWld OBJECT-TYPE
  SYNTAX DisplayString
  ACCESS read-write
  STATUS mandatory
  DESCRIPTION
    "Variable name: STEALTH_L2_FILTER_EXTERN.DEST_MAC
    WebUi Label: Destination MAC
    Destination MAC Address to apply this filter rule for. The special
    string 'xx' for an octet matches any value."
  ::= { mGuardL2FilterExternEntry 9 }

-- STEALTH_L2_FILTER_EXTERN.TARGET
mGuardL2FilterExternTarget OBJECT-TYPE
  SYNTAX INTEGER {
    accept(1),
    drop(3)
  }
  ACCESS read-write
  STATUS mandatory
  DESCRIPTION
    "Variable name: STEALTH_L2_FILTER_EXTERN.TARGET
    WebUi Label: Action
    The target of the rule (accept/drop)."
  ::= { mGuardL2FilterExternEntry 6 }


-- STEALTH_L2_FILTER_INTERN table
mGuardL2FilterInternTable OBJECT-TYPE
  SYNTAX SEQUENCE OF MGuardL2FilterInternEntry
  ACCESS not-accessible
  STATUS mandatory
  DESCRIPTION
    "A table of STEALTH_L2_FILTER_INTERN"
  ::= { mGuardStealthL2Filter 1 }

-- STEALTH_L2_FILTER_INTERN table entry
mGuardL2FilterInternEntry OBJECT-TYPE
  SYNTAX MGuardL2FilterInternEntry
  ACCESS not-accessible
  STATUS mandatory
  DESCRIPTION
    "An entry of STEALTH_L2_FILTER_INTERN"
  INDEX { mGuardL2FilterInternRuleIndex }
  ::= { mGuardL2FilterInternTable 1 }

MGuardL2FilterInternEntry ::= SEQUENCE {
  mGuardL2FilterInternRuleIndex            INTEGER,
  mGuardL2FilterInternRowStatus            RowStatus,
  mGuardL2FilterInternTarget               INTEGER,
  mGuardL2FilterInternComment              DisplayString,
  mGuardL2FilterInternSrcMacWld            DisplayString,
  mGuardL2FilterInternDstMacWld            DisplayString,
  mGuardL2FilterInternEthProto             DisplayString
}

-- STEALTH_L2_FILTER_INTERN table index
mGuardL2FilterInternRuleIndex OBJECT-TYPE
  SYNTAX INTEGER (1..2147483647)
  ACCESS not-accessible
  STATUS mandatory
  DESCRIPTION
    "Index to STEALTH_L2_FILTER_INTERN"
  ::= { mGuardL2FilterInternEntry 1 }

-- STEALTH_L2_FILTER_INTERN row status
mGuardL2FilterInternRowStatus OBJECT-TYPE
  SYNTAX RowStatus
  ACCESS read-write
  STATUS mandatory
  DESCRIPTION
    "RowStatus of STEALTH_L2_FILTER_INTERN"
  ::= { mGuardL2FilterInternEntry 2 }

-- STEALTH_L2_FILTER_INTERN.COMMENT
mGuardL2FilterInternComment OBJECT-TYPE
  SYNTAX DisplayString
  ACCESS read-write
  STATUS mandatory
  DESCRIPTION
    "Variable name: STEALTH_L2_FILTER_INTERN.COMMENT
    WebUi Label: Comment
    Comment or name for this rule."
  ::= { mGuardL2FilterInternEntry 7 }

-- STEALTH_L2_FILTER_INTERN.SOURCE_MAC
mGuardL2FilterInternSrcMacWld OBJECT-TYPE
  SYNTAX DisplayString
  ACCESS read-write
  STATUS mandatory
  DESCRIPTION
    "Variable name: STEALTH_L2_FILTER_INTERN.SOURCE_MAC
    WebUi Label: Source MAC
    Source MAC Address to apply this filter rule for. The special string
    'xx' for an octet matches any value."
  ::= { mGuardL2FilterInternEntry 8 }

-- STEALTH_L2_FILTER_INTERN.ETHERTYPE_HEX
mGuardL2FilterInternEthProto OBJECT-TYPE
  SYNTAX DisplayString
  ACCESS read-write
  STATUS mandatory
  DESCRIPTION
    "Variable name: STEALTH_L2_FILTER_INTERN.ETHERTYPE_HEX
    WebUi Label: Ethernet protocol
    Ethernet type to apply this filter rule for."
  ::= { mGuardL2FilterInternEntry 10 }

-- STEALTH_L2_FILTER_INTERN.DEST_MAC
mGuardL2FilterInternDstMacWld OBJECT-TYPE
  SYNTAX DisplayString
  ACCESS read-write
  STATUS mandatory
  DESCRIPTION
    "Variable name: STEALTH_L2_FILTER_INTERN.DEST_MAC
    WebUi Label: Destination MAC
    Destination MAC Address to apply this filter rule for. The special
    string 'xx' for an octet matches any value."
  ::= { mGuardL2FilterInternEntry 9 }

-- STEALTH_L2_FILTER_INTERN.TARGET
mGuardL2FilterInternTarget OBJECT-TYPE
  SYNTAX INTEGER {
    accept(1),
    drop(3)
  }
  ACCESS read-write
  STATUS mandatory
  DESCRIPTION
    "Variable name: STEALTH_L2_FILTER_INTERN.TARGET
    WebUi Label: Action
    The target of the rule (accept/drop)."
  ::= { mGuardL2FilterInternEntry 6 }

-- STEALTH_MAC
mGuardStealthStaticMAC OBJECT-TYPE
  SYNTAX MacAddress
  ACCESS read-write
  STATUS mandatory
  DESCRIPTION
    "Variable name: STEALTH_MAC
    WebUi Label: Client's MAC address
    MAC address of protected client in stealth mode (using static ip
    configuration)."
  ::= { mGuardStealthIPConfStatic 2 }


-- STEALTH_MANAGE_ALIASES table
mGuardStealthManageAliasesTable OBJECT-TYPE
  SYNTAX SEQUENCE OF MGuardStealthManageAliasesEntry
  ACCESS not-accessible
  STATUS mandatory
  DESCRIPTION
    "A table of STEALTH_MANAGE_ALIASES"
  ::= { mGuardStealthInterface 7 }

-- STEALTH_MANAGE_ALIASES table entry
mGuardStealthManageAliasesEntry OBJECT-TYPE
  SYNTAX MGuardStealthManageAliasesEntry
  ACCESS not-accessible
  STATUS mandatory
  DESCRIPTION
    "An entry of STEALTH_MANAGE_ALIASES"
  INDEX { mGuardStealthAliasIndex }
  ::= { mGuardStealthManageAliasesTable 1 }

MGuardStealthManageAliasesEntry ::= SEQUENCE {
  mGuardStealthAliasIndex                  INTEGER,
  mGuardStealthAliasIpAddress              IpAddress,
  mGuardStealthAliasNetmask                IpAddress,
  mGuardStealthAliasRowStatus              RowStatus,
  mGuardStealthAliasUseVLAN                INTEGER,
  mGuardStealthAliasVLANid                 INTEGER
}

-- STEALTH_MANAGE_ALIASES table index
mGuardStealthAliasIndex OBJECT-TYPE
  SYNTAX INTEGER (1..2147483647)
  ACCESS not-accessible
  STATUS mandatory
  DESCRIPTION
    "Index to STEALTH_MANAGE_ALIASES"
  ::= { mGuardStealthManageAliasesEntry 1 }

-- STEALTH_MANAGE_ALIASES row status
mGuardStealthAliasRowStatus OBJECT-TYPE
  SYNTAX RowStatus
  ACCESS read-write
  STATUS mandatory
  DESCRIPTION
    "RowStatus of STEALTH_MANAGE_ALIASES"
  ::= { mGuardStealthManageAliasesEntry 4 }

-- STEALTH_MANAGE_ALIASES.MANAGE_IP
mGuardStealthAliasIpAddress OBJECT-TYPE
  SYNTAX IpAddress
  ACCESS read-write
  STATUS mandatory
  DESCRIPTION
    "Variable name: STEALTH_MANAGE_ALIASES.MANAGE_IP
    WebUi Label: IP address
    IP address."
  ::= { mGuardStealthManageAliasesEntry 2 }

-- STEALTH_MANAGE_ALIASES.USE_VLAN
mGuardStealthAliasUseVLAN OBJECT-TYPE
  SYNTAX INTEGER {
    yes(1),
    no(2)
  }
  ACCESS read-write
  STATUS mandatory
  DESCRIPTION
    "Variable name: STEALTH_MANAGE_ALIASES.USE_VLAN
    WebUi Label: Use VLAN
    Use VLAN tagging with this Alias interface."
  ::= { mGuardStealthManageAliasesEntry 5 }

-- STEALTH_MANAGE_ALIASES.VLAN_ID
mGuardStealthAliasVLANid OBJECT-TYPE
  SYNTAX INTEGER(1..4094)
  ACCESS read-write
  STATUS mandatory
  DESCRIPTION
    "Variable name: STEALTH_MANAGE_ALIASES.VLAN_ID
    WebUi Label: VLAN ID
    VLAN ID to be used with this Alias."
  ::= { mGuardStealthManageAliasesEntry 6 }

-- STEALTH_MANAGE_ALIASES.MANAGE_NET
mGuardStealthAliasNetmask OBJECT-TYPE
  SYNTAX IpAddress
  ACCESS read-write
  STATUS mandatory
  DESCRIPTION
    "Variable name: STEALTH_MANAGE_ALIASES.MANAGE_NET
    WebUi Label: Netmask
    Netmask."
  ::= { mGuardStealthManageAliasesEntry 3 }

-- STEALTH_MANAGE_GW
mGuardStealthManageGateway OBJECT-TYPE
  SYNTAX IpAddress
  ACCESS read-write
  STATUS mandatory
  DESCRIPTION
    "Variable name: STEALTH_MANAGE_GW
    WebUi Label: Default gateway
    The default gateway for the management IP of the mGuard in stealth
    mode."
  ::= { mGuardStealthIPConfStatic 6 }

-- STEALTH_MANAGE_IP
mGuardStealthManageIP OBJECT-TYPE
  SYNTAX IpAddress
  ACCESS read-write
  STATUS mandatory
  DESCRIPTION
    "Variable name: STEALTH_MANAGE_IP
    WebUi Label: --
    The management IP address of this system in stealth mode."
  ::= { mGuardStealthIPConfStatic 4 }

-- STEALTH_MANAGE_NET
mGuardStealthManageNetmask OBJECT-TYPE
  SYNTAX IpAddress
  ACCESS read-write
  STATUS mandatory
  DESCRIPTION
    "Variable name: STEALTH_MANAGE_NET
    WebUi Label: --
    The management IP netmask of this system in stealth mode."
  ::= { mGuardStealthIPConfStatic 5 }

-- STEALTH_MANAGE_USE_VLAN
mGuardStealthManageUseVLAN OBJECT-TYPE
  SYNTAX INTEGER {
    yes(1),
    no(2)
  }
  ACCESS read-write
  STATUS mandatory
  DESCRIPTION
    "Variable name: STEALTH_MANAGE_USE_VLAN
    WebUi Label: --
    Use VLAN tagging for the management IP address in Stealth Mode."
  ::= { mGuardStealthInterface 3 }

-- STEALTH_MANAGE_VLAN_ID
mGuardStealthManageVLanID OBJECT-TYPE
  SYNTAX INTEGER(1..4094)
  ACCESS read-write
  STATUS mandatory
  DESCRIPTION
    "Variable name: STEALTH_MANAGE_VLAN_ID
    WebUi Label: --
    VLAN ID for the management IP address in Stealth Mode."
  ::= { mGuardStealthInterface 4 }

-- STEALTH_MODE
mGuardStealthIPConfMode OBJECT-TYPE
  SYNTAX INTEGER {
    autoDetect(1),
    static(2),
    multi(3)
  }
  ACCESS read-write
  STATUS mandatory
  DESCRIPTION
    "Variable name: STEALTH_MODE
    WebUi Label: Stealth configuration
    Type of IP Stack configuration in stealth mode. autodetect, static,
    multiple-clients"
  ::= { mGuardStealth 1 }

-- STEALTH_MTU
mGuardStealthMTU OBJECT-TYPE
  SYNTAX INTEGER(46..1500)
  ACCESS read-write
  STATUS mandatory
  DESCRIPTION
    "Variable name: STEALTH_MTU
    WebUi Label: MTU of the management interface
    MTU to use in Stealth Mode."
  ::= { mGuardStealthInterface 1 }

-- STEALTH_VLAN_MTU
mGuardStealthVlanMTU OBJECT-TYPE
  SYNTAX INTEGER(46..1500)
  ACCESS read-write
  STATUS mandatory
  DESCRIPTION
    "Variable name: STEALTH_VLAN_MTU
    WebUi Label: MTU of the management interface for VLAN
    MTU to use in Stealth Mode for VLAN packets."
  ::= { mGuardStealthInterface 2 }

-- SYSTEM_USE_NOTIFICATION
mGuardSystemUseNotification OBJECT-TYPE
  SYNTAX DisplayString
  ACCESS read-write
  STATUS mandatory
  DESCRIPTION
    "Variable name: SYSTEM_USE_NOTIFICATION
    WebUi Label: System use notification
    This note will be displayed before login via SSH, HTTPS, Serial
    console"
  ::= { mGuardNetwork 18 }

-- TIMEZONE
mGuardNTPTimezone OBJECT-TYPE
  SYNTAX DisplayString
  ACCESS read-write
  STATUS mandatory
  DESCRIPTION
    "Variable name: TIMEZONE
    WebUi Label: Timezone in POSIX.1 notation
    Timezone in POSIX.1 notation"
  ::= { mGuardNTP 4 }

-- USERFW_ENABLE
mGuardFWUsrFWEnabled OBJECT-TYPE
  SYNTAX INTEGER {
    yes(1),
    no(2)
  }
  ACCESS read-write
  STATUS mandatory
  DESCRIPTION
    "Variable name: USERFW_ENABLE
    WebUi Label: Enable user firewall
    Enable the user firewall."
  ::= { mGuardFWUsrFW 1 }

-- USERFW_GROUP_AUTH_ENABLE
mGuardFWUsrFWGroupAuthEnabled OBJECT-TYPE
  SYNTAX INTEGER {
    yes(1),
    no(2)
  }
  ACCESS read-write
  STATUS mandatory
  DESCRIPTION
    "Variable name: USERFW_GROUP_AUTH_ENABLE
    WebUi Label: Enable group authentication
    Enable Group Authentication for the user firewall."
  ::= { mGuardFWUsrFW 5 }


-- USERFW_INTERFACES table
mGuardFWUsrFWIFTable OBJECT-TYPE
  SYNTAX SEQUENCE OF MGuardFWUsrFWIFEntry
  ACCESS not-accessible
  STATUS mandatory
  DESCRIPTION
    "A table of USERFW_INTERFACES"
  ::= { mGuardFWUsrFW 6 }

-- USERFW_INTERFACES table entry
mGuardFWUsrFWIFEntry OBJECT-TYPE
  SYNTAX MGuardFWUsrFWIFEntry
  ACCESS not-accessible
  STATUS mandatory
  DESCRIPTION
    "An entry of USERFW_INTERFACES"
  INDEX { mGuardFWUsrFWIFIndex }
  ::= { mGuardFWUsrFWIFTable 1 }

MGuardFWUsrFWIFEntry ::= SEQUENCE {
  mGuardFWUsrFWIFIndex                     INTEGER,
  mGuardFWUsrFWIFRowStatus                 RowStatus,
  mGuardFWUsrFWIFInterface                 INTEGER
}

-- USERFW_INTERFACES table index
mGuardFWUsrFWIFIndex OBJECT-TYPE
  SYNTAX INTEGER (1..2147483647)
  ACCESS not-accessible
  STATUS mandatory
  DESCRIPTION
    "Index to USERFW_INTERFACES"
  ::= { mGuardFWUsrFWIFEntry 1 }

-- USERFW_INTERFACES row status
mGuardFWUsrFWIFRowStatus OBJECT-TYPE
  SYNTAX RowStatus
  ACCESS read-write
  STATUS mandatory
  DESCRIPTION
    "RowStatus of USERFW_INTERFACES"
  ::= { mGuardFWUsrFWIFEntry 3 }

-- USERFW_INTERFACES.INTERFACE
mGuardFWUsrFWIFInterface OBJECT-TYPE
  SYNTAX INTEGER {
    int(1),
    ext1(2),
    ext2(3),
    dialin(4),
    dmz0(5),
    ipsec(6)
  }
  ACCESS read-write
  STATUS mandatory
  DESCRIPTION
    "Variable name: USERFW_INTERFACES.INTERFACE
    WebUi Label: Interface
    Interface."
  ::= { mGuardFWUsrFWIFEntry 4 }


-- USERFW_TEMPLATE table
mGuardFWUsrFWTmplTable OBJECT-TYPE
  SYNTAX SEQUENCE OF MGuardFWUsrFWTmplEntry
  ACCESS not-accessible
  STATUS mandatory
  DESCRIPTION
    "A table of USERFW_TEMPLATE"
  ::= { mGuardFWUsrFW 2 }

-- USERFW_TEMPLATE table entry
mGuardFWUsrFWTmplEntry OBJECT-TYPE
  SYNTAX MGuardFWUsrFWTmplEntry
  ACCESS not-accessible
  STATUS mandatory
  DESCRIPTION
    "An entry of USERFW_TEMPLATE"
  INDEX { mGuardFWUsrFWTmplIndex }
  ::= { mGuardFWUsrFWTmplTable 1 }

MGuardFWUsrFWTmplEntry ::= SEQUENCE {
  mGuardFWUsrFWTmplIndex                   INTEGER,
  mGuardFWUsrFWTmplEnabled                 INTEGER,
  mGuardFWUsrFWTmplName                    DisplayString,
  mGuardFWUsrFWTmplComment                 DisplayString,
  mGuardFWUsrFWTmplTimeout                 INTEGER,
  mGuardFWUsrFWTmplSrcIP                   DisplayString,
  mGuardFWUsrFWTmplRowStatus               RowStatus,
  mGuardFWUsrFWTmplTimeOutType             INTEGER,
  mGuardFWUsrFWTmplUUID                    DisplayString,
  mGuardFWUsrFWTmplVPNconValue             INTEGER,
  mGuardFWUsrFWTmplVPNconRef               OBJECT IDENTIFIER
}

-- USERFW_TEMPLATE table index
mGuardFWUsrFWTmplIndex OBJECT-TYPE
  SYNTAX INTEGER (1..2147483647)
  ACCESS not-accessible
  STATUS mandatory
  DESCRIPTION
    "Index to USERFW_TEMPLATE"
  ::= { mGuardFWUsrFWTmplEntry 1 }

-- USERFW_TEMPLATE row status
mGuardFWUsrFWTmplRowStatus OBJECT-TYPE
  SYNTAX RowStatus
  ACCESS read-write
  STATUS mandatory
  DESCRIPTION
    "RowStatus of USERFW_TEMPLATE"
  ::= { mGuardFWUsrFWTmplEntry 7 }

-- USERFW_TEMPLATE.VPN_CONN_REF
mGuardFWUsrFWTmplVPNconValue OBJECT-TYPE
  SYNTAX INTEGER {
    none(1)
  }
  ACCESS read-write
  STATUS mandatory
  DESCRIPTION
    "Variable name: USERFW_TEMPLATE.VPN_CONN_REF
    WebUi Label: VPN connection
    When read, this object will always return 'none'. Set this object to
    'none' to disable any association of this user firewall template with
    a vpn connection in the object 'mGuardFWUsrFWTmplVPNconRef'."
  ::= { mGuardFWUsrFWTmplEntry 10 }

-- USERFW_TEMPLATE.VPN_CONN_REF reference
mGuardFWUsrFWTmplVPNconRef OBJECT-TYPE
  SYNTAX OBJECT IDENTIFIER
  ACCESS read-write
  STATUS mandatory
  DESCRIPTION
    "Variable name: USERFW_TEMPLATE.VPN_CONN_REF
    WebUi Label: VPN connection
    To limit the validity of this user firewall template to a VPN
    connection, write the OID of a 'mGuardVPNconIndex' or
    'mGuardOpenVPNConnectionIndex' to this object. To disable this feature
    and make the validity of the user firewall template global, write the
    'mGuardFWUsrFwTmpVPNconValue' object."
  ::= { mGuardFWUsrFWTmplEntry 11 }

-- USERFW_TEMPLATE.TEMPLATE_TIMEOUT
mGuardFWUsrFWTmplTimeout OBJECT-TYPE
  SYNTAX INTEGER(1..86400)
  ACCESS read-write
  STATUS mandatory
  DESCRIPTION
    "Variable name: USERFW_TEMPLATE.TEMPLATE_TIMEOUT
    WebUi Label: Timeout
    The timeout in seconds of the user firewall template."
  ::= { mGuardFWUsrFWTmplEntry 5 }

-- USERFW_TEMPLATE.TEMPLATE_NAME
mGuardFWUsrFWTmplName OBJECT-TYPE
  SYNTAX DisplayString
  ACCESS read-write
  STATUS mandatory
  DESCRIPTION
    "Variable name: USERFW_TEMPLATE.TEMPLATE_NAME
    WebUi Label: A descriptive name
    A descriptive name of the user firewall template."
  ::= { mGuardFWUsrFWTmplEntry 3 }

-- USERFW_TEMPLATE.TEMPLATE_TOUT_TYPE
mGuardFWUsrFWTmplTimeOutType OBJECT-TYPE
  SYNTAX INTEGER {
    static(1),
    dynamic(2)
  }
  ACCESS read-write
  STATUS mandatory
  DESCRIPTION
    "Variable name: USERFW_TEMPLATE.TEMPLATE_TOUT_TYPE
    WebUi Label: Timeout type
    Use static or dynamic timeout for this template."
  ::= { mGuardFWUsrFWTmplEntry 8 }


-- USERFW_TEMPLATE.TEMPLATE_USERS table
mGuardFWUsrFWTmplUserTable OBJECT-TYPE
  SYNTAX SEQUENCE OF MGuardFWUsrFWTmplUserEntry
  ACCESS not-accessible
  STATUS mandatory
  DESCRIPTION
    "A table of USERFW_TEMPLATE.TEMPLATE_USERS"
  ::= { mGuardFWUsrFW 3 }

-- USERFW_TEMPLATE.TEMPLATE_USERS table entry
mGuardFWUsrFWTmplUserEntry OBJECT-TYPE
  SYNTAX MGuardFWUsrFWTmplUserEntry
  ACCESS not-accessible
  STATUS mandatory
  DESCRIPTION
    "An entry of USERFW_TEMPLATE.TEMPLATE_USERS"
  INDEX { mGuardFWUsrFWTmplIndex, mGuardFWUsrFWTmplUserIndex }
  ::= { mGuardFWUsrFWTmplUserTable 1 }

MGuardFWUsrFWTmplUserEntry ::= SEQUENCE {
  mGuardFWUsrFWTmplUserIndex               INTEGER,
  mGuardFWUsrFWTmplUserName                DisplayString,
  mGuardFWUsrFWTmplUserRowStatus           RowStatus
}

-- USERFW_TEMPLATE.TEMPLATE_USERS table index
mGuardFWUsrFWTmplUserIndex OBJECT-TYPE
  SYNTAX INTEGER (1..2147483647)
  ACCESS not-accessible
  STATUS mandatory
  DESCRIPTION
    "Index to USERFW_TEMPLATE.TEMPLATE_USERS"
  ::= { mGuardFWUsrFWTmplUserEntry 2 }

-- USERFW_TEMPLATE.TEMPLATE_USERS row status
mGuardFWUsrFWTmplUserRowStatus OBJECT-TYPE
  SYNTAX RowStatus
  ACCESS read-write
  STATUS mandatory
  DESCRIPTION
    "RowStatus of USERFW_TEMPLATE.TEMPLATE_USERS"
  ::= { mGuardFWUsrFWTmplUserEntry 4 }

-- USERFW_TEMPLATE.TEMPLATE_USERS.USERNAME
mGuardFWUsrFWTmplUserName OBJECT-TYPE
  SYNTAX DisplayString
  ACCESS read-write
  STATUS mandatory
  DESCRIPTION
    "Variable name: USERFW_TEMPLATE.TEMPLATE_USERS.USERNAME
    WebUi Label: User
    The username of the user within the user firewall template entry."
  ::= { mGuardFWUsrFWTmplUserEntry 3 }

-- USERFW_TEMPLATE.TEMPLATE_RULE
mGuardFWUsrFWTmplUUID OBJECT-TYPE
  SYNTAX DisplayString
  ACCESS read-only
  STATUS mandatory
  DESCRIPTION
    "Variable name: USERFW_TEMPLATE.TEMPLATE_RULE
    WebUi Label: --
    Universally Unique Identifier (UUID, RFC 4122) used for
    'MGuardFWUsrFWTmplRuleTable' logging."
  ::= { mGuardFWUsrFWTmplEntry 9 }


-- USERFW_TEMPLATE.TEMPLATE_RULE table
mGuardFWUsrFWTmplRuleTable OBJECT-TYPE
  SYNTAX SEQUENCE OF MGuardFWUsrFWTmplRuleEntry
  ACCESS not-accessible
  STATUS mandatory
  DESCRIPTION
    "A table of USERFW_TEMPLATE.TEMPLATE_RULE"
  ::= { mGuardFWUsrFW 4 }

-- USERFW_TEMPLATE.TEMPLATE_RULE table entry
mGuardFWUsrFWTmplRuleEntry OBJECT-TYPE
  SYNTAX MGuardFWUsrFWTmplRuleEntry
  ACCESS not-accessible
  STATUS mandatory
  DESCRIPTION
    "An entry of USERFW_TEMPLATE.TEMPLATE_RULE"
  INDEX { mGuardFWUsrFWTmplIndex, mGuardFWUsrFWTmplRuleIndex }
  ::= { mGuardFWUsrFWTmplRuleTable 1 }

MGuardFWUsrFWTmplRuleEntry ::= SEQUENCE {
  mGuardFWUsrFWTmplRuleIndex               INTEGER,
  mGuardFWUsrFWTmplRuleProto               INTEGER,
  mGuardFWUsrFWTmplRuleLog                 INTEGER,
  mGuardFWUsrFWTmplRuleComment             DisplayString,
  mGuardFWUsrFWTmplRuleRowStatus           RowStatus,
  mGuardFWUsrFWTmplRuleDstIPOrGroupValue   DisplayString,
  mGuardFWUsrFWTmplRuleDstIPOrGroupRef     OBJECT IDENTIFIER,
  mGuardFWUsrFWTmplRuleSrcPortOrGroupValue DisplayString,
  mGuardFWUsrFWTmplRuleSrcPortOrGroupRef   OBJECT IDENTIFIER,
  mGuardFWUsrFWTmplRuleDstPortOrGroupValue DisplayString,
  mGuardFWUsrFWTmplRuleDstPortOrGroupRef   OBJECT IDENTIFIER
}

-- USERFW_TEMPLATE.TEMPLATE_RULE table index
mGuardFWUsrFWTmplRuleIndex OBJECT-TYPE
  SYNTAX INTEGER (1..2147483647)
  ACCESS not-accessible
  STATUS mandatory
  DESCRIPTION
    "Index to USERFW_TEMPLATE.TEMPLATE_RULE"
  ::= { mGuardFWUsrFWTmplRuleEntry 2 }

-- USERFW_TEMPLATE.TEMPLATE_RULE row status
mGuardFWUsrFWTmplRuleRowStatus OBJECT-TYPE
  SYNTAX RowStatus
  ACCESS read-write
  STATUS mandatory
  DESCRIPTION
    "RowStatus of USERFW_TEMPLATE.TEMPLATE_RULE"
  ::= { mGuardFWUsrFWTmplRuleEntry 9 }

-- USERFW_TEMPLATE.TEMPLATE_RULE.COMMENT
mGuardFWUsrFWTmplRuleComment OBJECT-TYPE
  SYNTAX DisplayString
  ACCESS read-write
  STATUS mandatory
  DESCRIPTION
    "Variable name: USERFW_TEMPLATE.TEMPLATE_RULE.COMMENT
    WebUi Label: Comment
    A comment associated with the rule within the user firewall template
    entry."
  ::= { mGuardFWUsrFWTmplRuleEntry 8 }

-- USERFW_TEMPLATE.TEMPLATE_RULE.SRC_PORT
mGuardFWUsrFWTmplRuleSrcPortOrGroupValue OBJECT-TYPE
  SYNTAX DisplayString
  ACCESS read-write
  STATUS mandatory
  DESCRIPTION
    "Variable name: USERFW_TEMPLATE.TEMPLATE_RULE.SRC_PORT
    WebUi Label: From port
    The source port or port range of the rule within the user firewall
    template entry."
  ::= { mGuardFWUsrFWTmplRuleEntry 20 }

-- USERFW_TEMPLATE.TEMPLATE_RULE.SRC_PORT reference
mGuardFWUsrFWTmplRuleSrcPortOrGroupRef OBJECT-TYPE
  SYNTAX OBJECT IDENTIFIER
  ACCESS read-write
  STATUS mandatory
  DESCRIPTION
    "Variable name: USERFW_TEMPLATE.TEMPLATE_RULE.SRC_PORT
    WebUi Label: From port
    The source port or port range of the rule within the user firewall
    template entry as reference to port group."
  ::= { mGuardFWUsrFWTmplRuleEntry 21 }

-- USERFW_TEMPLATE.TEMPLATE_RULE.LOG
mGuardFWUsrFWTmplRuleLog OBJECT-TYPE
  SYNTAX INTEGER {
    yes(1),
    no(2)
  }
  ACCESS read-write
  STATUS mandatory
  DESCRIPTION
    "Variable name: USERFW_TEMPLATE.TEMPLATE_RULE.LOG
    WebUi Label: Log
    Log packets matching the rule within the user firewall template entry."
  ::= { mGuardFWUsrFWTmplRuleEntry 7 }

-- USERFW_TEMPLATE.TEMPLATE_RULE.PROTO
mGuardFWUsrFWTmplRuleProto OBJECT-TYPE
  SYNTAX INTEGER {
    tcp(1),
    udp(2),
    icmp(3),
    all(4),
    gre(5)
  }
  ACCESS read-write
  STATUS mandatory
  DESCRIPTION
    "Variable name: USERFW_TEMPLATE.TEMPLATE_RULE.PROTO
    WebUi Label: Protocol
    The protocol of the rule within the user firewall template entry."
  ::= { mGuardFWUsrFWTmplRuleEntry 3 }

-- USERFW_TEMPLATE.TEMPLATE_RULE.DST_PORT
mGuardFWUsrFWTmplRuleDstPortOrGroupValue OBJECT-TYPE
  SYNTAX DisplayString
  ACCESS read-write
  STATUS mandatory
  DESCRIPTION
    "Variable name: USERFW_TEMPLATE.TEMPLATE_RULE.DST_PORT
    WebUi Label: To port
    The destination port or port range of the rule within the user
    firewall template entry."
  ::= { mGuardFWUsrFWTmplRuleEntry 22 }

-- USERFW_TEMPLATE.TEMPLATE_RULE.DST_PORT reference
mGuardFWUsrFWTmplRuleDstPortOrGroupRef OBJECT-TYPE
  SYNTAX OBJECT IDENTIFIER
  ACCESS read-write
  STATUS mandatory
  DESCRIPTION
    "Variable name: USERFW_TEMPLATE.TEMPLATE_RULE.DST_PORT
    WebUi Label: To port
    The destination port or port range of the rule within the user
    firewall template entry as reference to port group."
  ::= { mGuardFWUsrFWTmplRuleEntry 23 }

-- USERFW_TEMPLATE.TEMPLATE_RULE.DST_IP
mGuardFWUsrFWTmplRuleDstIPOrGroupValue OBJECT-TYPE
  SYNTAX DisplayString
  ACCESS read-write
  STATUS mandatory
  DESCRIPTION
    "Variable name: USERFW_TEMPLATE.TEMPLATE_RULE.DST_IP
    WebUi Label: To IP
    The destination IP address of the rule within the user firewall
    template entry."
  ::= { mGuardFWUsrFWTmplRuleEntry 18 }

-- USERFW_TEMPLATE.TEMPLATE_RULE.DST_IP reference
mGuardFWUsrFWTmplRuleDstIPOrGroupRef OBJECT-TYPE
  SYNTAX OBJECT IDENTIFIER
  ACCESS read-write
  STATUS mandatory
  DESCRIPTION
    "Variable name: USERFW_TEMPLATE.TEMPLATE_RULE.DST_IP
    WebUi Label: To IP
    The destination IP address of the rule within the user firewall
    template entry as reference to IP group."
  ::= { mGuardFWUsrFWTmplRuleEntry 19 }

-- USERFW_TEMPLATE.TEMPLATE_SRC_IP
mGuardFWUsrFWTmplSrcIP OBJECT-TYPE
  SYNTAX DisplayString
  ACCESS read-write
  STATUS mandatory
  DESCRIPTION
    "Variable name: USERFW_TEMPLATE.TEMPLATE_SRC_IP
    WebUi Label: Source IP
    The source IP address of the user firewall template."
  ::= { mGuardFWUsrFWTmplEntry 6 }

-- USERFW_TEMPLATE.TEMPLATE_ENABLED
mGuardFWUsrFWTmplEnabled OBJECT-TYPE
  SYNTAX INTEGER {
    yes(1),
    no(2)
  }
  ACCESS read-write
  STATUS mandatory
  DESCRIPTION
    "Variable name: USERFW_TEMPLATE.TEMPLATE_ENABLED
    WebUi Label: Enabled
    Enable this user firewall template."
  ::= { mGuardFWUsrFWTmplEntry 2 }

-- USERFW_TEMPLATE.TEMPLATE_COMMENT
mGuardFWUsrFWTmplComment OBJECT-TYPE
  SYNTAX DisplayString
  ACCESS read-write
  STATUS mandatory
  DESCRIPTION
    "Variable name: USERFW_TEMPLATE.TEMPLATE_COMMENT
    WebUi Label: Comment
    A comment associated with the user firewall template."
  ::= { mGuardFWUsrFWTmplEntry 4 }


-- USERFW_USERS table
mGuardUserFWUserTable OBJECT-TYPE
  SYNTAX SEQUENCE OF MGuardUserFWUserEntry
  ACCESS not-accessible
  STATUS mandatory
  DESCRIPTION
    "A table of USERFW_USERS"
  ::= { mGuardUserFWUsers 1 }

-- USERFW_USERS table entry
mGuardUserFWUserEntry OBJECT-TYPE
  SYNTAX MGuardUserFWUserEntry
  ACCESS not-accessible
  STATUS mandatory
  DESCRIPTION
    "An entry of USERFW_USERS"
  INDEX { mGuardUserFWUserIndex }
  ::= { mGuardUserFWUserTable 1 }

MGuardUserFWUserEntry ::= SEQUENCE {
  mGuardUserFWUserIndex                    INTEGER,
  mGuardUserFWUserName                     DisplayString,
  mGuardUserFWUserAuthMethod               INTEGER,
  mGuardUserFWUserPassword                 DisplayString,
  mGuardUserFWUserRowStatus                RowStatus
}

-- USERFW_USERS table index
mGuardUserFWUserIndex OBJECT-TYPE
  SYNTAX INTEGER (1..2147483647)
  ACCESS not-accessible
  STATUS mandatory
  DESCRIPTION
    "Index to USERFW_USERS"
  ::= { mGuardUserFWUserEntry 1 }

-- USERFW_USERS row status
mGuardUserFWUserRowStatus OBJECT-TYPE
  SYNTAX RowStatus
  ACCESS read-write
  STATUS mandatory
  DESCRIPTION
    "RowStatus of USERFW_USERS"
  ::= { mGuardUserFWUserEntry 5 }

-- USERFW_USERS.USERNAME
mGuardUserFWUserName OBJECT-TYPE
  SYNTAX DisplayString
  ACCESS read-write
  STATUS mandatory
  DESCRIPTION
    "Variable name: USERFW_USERS.USERNAME
    WebUi Label: User name
    The username of the user firewall user entry."
  ::= { mGuardUserFWUserEntry 2 }

-- USERFW_USERS.AUTHMETHOD
mGuardUserFWUserAuthMethod OBJECT-TYPE
  SYNTAX INTEGER {
    radius(1),
    local(2)
  }
  ACCESS read-write
  STATUS mandatory
  DESCRIPTION
    "Variable name: USERFW_USERS.AUTHMETHOD
    WebUi Label: Authentication method
    The authentication method of the user firewall user entry."
  ::= { mGuardUserFWUserEntry 3 }

-- USERFW_USERS.PASSWORD
mGuardUserFWUserPassword OBJECT-TYPE
  SYNTAX DisplayString
  ACCESS read-write
  STATUS mandatory
  DESCRIPTION
    "Variable name: USERFW_USERS.PASSWORD
    WebUi Label: --
    The password of the user firewall user entry. The password can be set,
    but not obtained. If the variable is read, a * character is returned."
  ::= { mGuardUserFWUserEntry 4 }

-- USER_LOGIN_REQUIRED
mGuardUserPwdEnable OBJECT-TYPE
  SYNTAX INTEGER {
    yes(1),
    no(2)
  }
  ACCESS read-write
  STATUS mandatory
  DESCRIPTION
    "Variable name: USER_LOGIN_REQUIRED
    WebUi Label: Disable VPN until the user is authenticated via HTTP
    Disable VPN until the user is authenticated via HTTP? yes, no"
  ::= { mGuardPasswords 4 }

-- USER_PASSWORD
mGuardUserPassword OBJECT-TYPE
  SYNTAX DisplayString
  ACCESS read-write
  STATUS mandatory
  DESCRIPTION
    "Variable name: USER_PASSWORD
    WebUi Label: User password
    Changes the password for the user 'user', who can be used to avoid
    automatic start of the VPN. This feature is intended to be used in
    road warrior scenarios."
  ::= { mGuardPasswords 3 }

-- VPN_ALWAYS_SEND_NATOA
mGuardVPNAlwaysSendNATOA OBJECT-TYPE
  SYNTAX INTEGER {
    yes(1),
    no(2)
  }
  ACCESS read-write
  STATUS mandatory
  DESCRIPTION
    "Variable name: VPN_ALWAYS_SEND_NATOA
    WebUi Label: Always send NAT-OA payloads with NAT-T
    According to RFC3947 NAT-OA records are only sent for transport
    connections. Setting to 'off' keeps the RFC3947 behavior. Setting to
    'proprietary' causes NAT-OA records to be sent for all cases of NAT-T
    between mGuard devices supporting this feature. This may reveal
    information about the network structure behind the NAT gateway."
  ::= { mGuardVPNSettings 37 }


-- VPN_CONNECTION table
mGuardVPNConnectionTable OBJECT-TYPE
  SYNTAX SEQUENCE OF MGuardVPNConnectionEntry
  ACCESS not-accessible
  STATUS mandatory
  DESCRIPTION
    "A table of VPN_CONNECTION"
  ::= { mGuardVPN 2 }

-- VPN_CONNECTION table entry
mGuardVPNConnectionEntry OBJECT-TYPE
  SYNTAX MGuardVPNConnectionEntry
  ACCESS not-accessible
  STATUS mandatory
  DESCRIPTION
    "An entry of VPN_CONNECTION"
  INDEX { mGuardVPNconIndex }
  ::= { mGuardVPNConnectionTable 1 }

MGuardVPNConnectionEntry ::= SEQUENCE {
  mGuardVPNconIndex                        INTEGER,
  mGuardVPNconName                         DisplayString,
  mGuardVPNremGW                           DisplayString,
  mGuardVPNauthType                        INTEGER,
  mGuardVPNpsk                             DisplayString,
  mGuardVPNx509                            DisplayString,
  mGuardVPNpfs                             INTEGER,
  mGuardVPNconStartUp                      INTEGER,
  mGuardVPNFWLogDefIn                      INTEGER,
  mGuardVPNFWLogDefOut                     INTEGER,
  mGuardVPNProtoAH                         INTEGER,
  mGuardVPNProtoESP                        INTEGER,
  mGuardVPNComp                            INTEGER,
  mGuardVPNLocalID                         DisplayString,
  mGuardVPNRemoteID                        DisplayString,
  mGuardVPNIkeLifetime                     INTEGER,
  mGuardVPNIpsecLifetime                   INTEGER,
  mGuardVPNRekeyMargin                     INTEGER,
  mGuardVPNRekeyFuzz                       INTEGER,
  mGuardVPNKeyingTries                     INTEGER,
  mGuardVPNDPDDelay                        INTEGER,
  mGuardVPNDPDTimeout                      INTEGER,
  mGuardVPNRowStatus                       RowStatus,
  mGuardVPNAggressive                      INTEGER,
  mGuardVPNReplayWindow                    INTEGER,
  mGuardVPNRemoteIKEPort                   INTEGER,
  mGuardVPNForceUDP                        INTEGER,
  mGuardVPNIPtunClientEnable               INTEGER,
  mGuardVPNIPtunClientPort                 DisplayString,
  mGuardVPNLocalCertNewValue               INTEGER,
  mGuardVPNLocalCertNewRef                 OBJECT IDENTIFIER,
  mGuardVPNRemoteCACertValue               INTEGER,
  mGuardVPNRemoteCACertRef                 OBJECT IDENTIFIER,
  mGuardVPNInterface                       INTEGER,
  mGuardVPNIPsecHardLimit                  INTEGER,
  mGuardVPNRekeyMarginBytes                INTEGER,
  mGuardVPNHostIp                          IpAddress,
  mGuardVPNFwInGlobal                      INTEGER,
  mGuardVPNFwOutGlobal                     INTEGER,
  mGuardVPNconStart                        INTEGER,
  mGuardVPNconSmsToken                     DisplayString,
  mGuardVPNconControl                      DisplayString,
  mGuardVPNconControlInv                   INTEGER,
  mGuardVPNconModeCfgXauth                 INTEGER,
  mGuardVPNconModeCfgPoolTranchSize        INTEGER,
  mGuardVPNconModeCfgDNS1                  IpAddress,
  mGuardVPNconModeCfgDNS2                  IpAddress,
  mGuardVPNconModeCfgWINS1                 IpAddress,
  mGuardVPNconModeCfgWINS2                 IpAddress,
  mGuardVPNconModeCfgServerLocal           INTEGER,
  mGuardVPNconModeCfgServerRemote          INTEGER,
  mGuardVPNconModeCfgClientRemote          INTEGER,
  mGuardVPNTimeoutSeconds                  INTEGER,
  mGuardVPNFWINuuid                        DisplayString,
  mGuardVPNFWOUTuuid                       DisplayString
}

-- VPN_CONNECTION table index
mGuardVPNconIndex OBJECT-TYPE
  SYNTAX INTEGER (1..2147483647)
  ACCESS not-accessible
  STATUS mandatory
  DESCRIPTION
    "Index to VPN_CONNECTION"
  ::= { mGuardVPNConnectionEntry 1 }

-- VPN_CONNECTION row status
mGuardVPNRowStatus OBJECT-TYPE
  SYNTAX RowStatus
  ACCESS read-write
  STATUS mandatory
  DESCRIPTION
    "RowStatus of VPN_CONNECTION"
  ::= { mGuardVPNConnectionEntry 42 }

-- VPN_CONNECTION.IPSECLIFETIME
mGuardVPNIpsecLifetime OBJECT-TYPE
  SYNTAX INTEGER(1..86400)
  ACCESS read-write
  STATUS mandatory
  DESCRIPTION
    "Variable name: VPN_CONNECTION.IPSECLIFETIME
    WebUi Label: IPsec SA lifetime
    IPsec SA lifetime in seconds."
  ::= { mGuardVPNConnectionEntry 34 }

-- VPN_CONNECTION.CERTIFICATE
mGuardVPNx509 OBJECT-TYPE
  SYNTAX DisplayString
  ACCESS read-write
  STATUS mandatory
  DESCRIPTION
    "Variable name: VPN_CONNECTION.CERTIFICATE
    WebUi Label: Remote certificate
    The X.509 certificate to be used when mGuardVPNLocalCertRef is set to
    'selfsigned'."
  ::= { mGuardVPNConnectionEntry 12 }


-- VPN_CONNECTION.MODECFG_SERVER_REMOTE_NETWORKS table
mGuardVPNModeCfgServerRemTable OBJECT-TYPE
  SYNTAX SEQUENCE OF MGuardVPNModeCfgServerRemEntry
  ACCESS not-accessible
  STATUS mandatory
  DESCRIPTION
    "A table of VPN_CONNECTION.MODECFG_SERVER_REMOTE_NETWORKS"
  ::= { mGuardVPNModeCfgServerRemNets 1 }

-- VPN_CONNECTION.MODECFG_SERVER_REMOTE_NETWORKS table entry
mGuardVPNModeCfgServerRemEntry OBJECT-TYPE
  SYNTAX MGuardVPNModeCfgServerRemEntry
  ACCESS not-accessible
  STATUS mandatory
  DESCRIPTION
    "An entry of VPN_CONNECTION.MODECFG_SERVER_REMOTE_NETWORKS"
  INDEX { mGuardVPNconIndex, mGuardVPNModeCfgServerRemIndex }
  ::= { mGuardVPNModeCfgServerRemTable 1 }

MGuardVPNModeCfgServerRemEntry ::= SEQUENCE {
  mGuardVPNModeCfgServerRemIndex           INTEGER,
  mGuardVPNModeCfgServerRemRowStatus       RowStatus,
  mGuardVPNModeCfgServerRemNet             DisplayString
}

-- VPN_CONNECTION.MODECFG_SERVER_REMOTE_NETWORKS table index
mGuardVPNModeCfgServerRemIndex OBJECT-TYPE
  SYNTAX INTEGER (1..2147483647)
  ACCESS not-accessible
  STATUS mandatory
  DESCRIPTION
    "Index to VPN_CONNECTION.MODECFG_SERVER_REMOTE_NETWORKS"
  ::= { mGuardVPNModeCfgServerRemEntry 1 }

-- VPN_CONNECTION.MODECFG_SERVER_REMOTE_NETWORKS row status
mGuardVPNModeCfgServerRemRowStatus OBJECT-TYPE
  SYNTAX RowStatus
  ACCESS read-write
  STATUS mandatory
  DESCRIPTION
    "RowStatus of VPN_CONNECTION.MODECFG_SERVER_REMOTE_NETWORKS"
  ::= { mGuardVPNModeCfgServerRemEntry 2 }

-- VPN_CONNECTION.MODECFG_SERVER_REMOTE_NETWORKS.NETWORK
mGuardVPNModeCfgServerRemNet OBJECT-TYPE
  SYNTAX DisplayString
  ACCESS read-write
  STATUS mandatory
  DESCRIPTION
    "Variable name: VPN_CONNECTION.MODECFG_SERVER_REMOTE_NETWORKS.NETWORK
    WebUi Label: Network
    The network in CIDR notation."
  ::= { mGuardVPNModeCfgServerRemEntry 3 }

-- VPN_CONNECTION.HOST_IP
mGuardVPNHostIp OBJECT-TYPE
  SYNTAX IpAddress
  ACCESS read-write
  STATUS mandatory
  DESCRIPTION
    "Variable name: VPN_CONNECTION.HOST_IP
    WebUi Label: IP address to use for gateway setting %any
    Specify the IP address to use for sending IKE packets from and to
    listen on for this VPN connection if mGuardVPNInterface is
    mGuardVPNInterface is byIp."
  ::= { mGuardVPNConnectionEntry 63 }

-- VPN_CONNECTION.IPTUN_ENABLE
mGuardVPNIPtunClientEnable OBJECT-TYPE
  SYNTAX INTEGER {
    yes(1),
    no(2),
    ncp(3)
  }
  ACCESS read-write
  STATUS mandatory
  DESCRIPTION
    "Variable name: VPN_CONNECTION.IPTUN_ENABLE
    WebUi Label: Encapsulate the VPN traffic in TCP
    Establish the VPN connection over a TCP tunnel."
  ::= { mGuardVPNConnectionEntry 54 }

-- VPN_CONNECTION.MODECFG_POOL_TRANCH_SIZE
mGuardVPNconModeCfgPoolTranchSize OBJECT-TYPE
  SYNTAX INTEGER(0..32)
  ACCESS read-write
  STATUS mandatory
  DESCRIPTION
    "Variable name: VPN_CONNECTION.MODECFG_POOL_TRANCH_SIZE
    WebUi Label: Tranches of size (network size between 0 and 32)
    MODECFG server mode: Configures the size of the address pool mask the
    MODECFG server chooses the dynamic address from. This value must be
    higher than or equal to the network mask of the remove network."
  ::= { mGuardVPNConnectionEntry 72 }

-- VPN_CONNECTION.IPSEC_HARD_LIMIT_BYTES
mGuardVPNIPsecHardLimit OBJECT-TYPE
  SYNTAX INTEGER(0..2147483647)
  ACCESS read-write
  STATUS mandatory
  DESCRIPTION
    "Variable name: VPN_CONNECTION.IPSEC_HARD_LIMIT_BYTES
    WebUi Label: IPsec SA traffic limit
    Maximum number of bytes an IPsec SA of this VPN connection may
    encrypt. Acceptable range is from 0 to 2147483647 bytes. The value
    zero disables the limit."
  ::= { mGuardVPNConnectionEntry 61 }

-- VPN_CONNECTION.REMOTE_ID
mGuardVPNRemoteID OBJECT-TYPE
  SYNTAX DisplayString
  ACCESS read-write
  STATUS mandatory
  DESCRIPTION
    "Variable name: VPN_CONNECTION.REMOTE_ID
    WebUi Label: Remote
    Local ID."
  ::= { mGuardVPNConnectionEntry 32 }

-- VPN_CONNECTION.IPTUN_DEST_PORT
mGuardVPNIPtunClientPort OBJECT-TYPE
  SYNTAX DisplayString
  ACCESS read-write
  STATUS mandatory
  DESCRIPTION
    "Variable name: VPN_CONNECTION.IPTUN_DEST_PORT
    WebUi Label: TCP-Port of the server, which accepts the encapsulated connection
    TCP destination port for IPsec over a TCP tunnel"
  ::= { mGuardVPNConnectionEntry 55 }


-- VPN_CONNECTION.TUNNEL table
mGuardVPNTunTable OBJECT-TYPE
  SYNTAX SEQUENCE OF MGuardVPNTunEntry
  ACCESS not-accessible
  STATUS mandatory
  DESCRIPTION
    "A table of VPN_CONNECTION.TUNNEL"
  ::= { mGuardVPNTunnel 1 }

-- VPN_CONNECTION.TUNNEL table entry
mGuardVPNTunEntry OBJECT-TYPE
  SYNTAX MGuardVPNTunEntry
  ACCESS not-accessible
  STATUS mandatory
  DESCRIPTION
    "An entry of VPN_CONNECTION.TUNNEL"
  INDEX { mGuardVPNconIndex, mGuardVPNTunRuleIndex }
  ::= { mGuardVPNTunTable 1 }

MGuardVPNTunEntry ::= SEQUENCE {
  mGuardVPNTunRuleIndex                    INTEGER,
  mGuardVPNTunEnable                       INTEGER,
  mGuardVPNTunType                         INTEGER,
  mGuardVPNTunLocal                        DisplayString,
  mGuardVPNTunRemote                       DisplayString,
  mGuardVPNTunVirtIP                       IpAddress,
  mGuardVPNTunRemote1to1Nat                IpAddress,
  mGuardVPNTunProto                        INTEGER,
  mGuardVPNTunLocalPort                    DisplayString,
  mGuardVPNTunRemotePort                   DisplayString,
  mGuardVPNTunDummyRoute                   INTEGER,
  mGuardVPNTunComment                      DisplayString,
  mGuardVPNTunRowStatus                    RowStatus,
  mGuardVPNTunLocalMasq                    DisplayString,
  mGuardVPNTunRemoteMasq                   IpAddress,
  mGuardVPNTunLocalNat                     INTEGER,
  mGuardVPNTunRemoteNat                    INTEGER
}

-- VPN_CONNECTION.TUNNEL table index
mGuardVPNTunRuleIndex OBJECT-TYPE
  SYNTAX INTEGER (1..2147483647)
  ACCESS not-accessible
  STATUS mandatory
  DESCRIPTION
    "Index to VPN_CONNECTION.TUNNEL"
  ::= { mGuardVPNTunEntry 2 }

-- VPN_CONNECTION.TUNNEL row status
mGuardVPNTunRowStatus OBJECT-TYPE
  SYNTAX RowStatus
  ACCESS read-write
  STATUS mandatory
  DESCRIPTION
    "RowStatus of VPN_CONNECTION.TUNNEL"
  ::= { mGuardVPNTunEntry 50 }

-- VPN_CONNECTION.TUNNEL.COMMENT
mGuardVPNTunComment OBJECT-TYPE
  SYNTAX DisplayString
  ACCESS read-write
  STATUS mandatory
  DESCRIPTION
    "Variable name: VPN_CONNECTION.TUNNEL.COMMENT
    WebUi Label: Comment
    Commentary or name for this connection."
  ::= { mGuardVPNTunEntry 49 }

-- VPN_CONNECTION.TUNNEL.REMOTE_1TO1NAT
mGuardVPNTunRemote1to1Nat OBJECT-TYPE
  SYNTAX IpAddress
  ACCESS read-write
  STATUS mandatory
  DESCRIPTION
    "Variable name: VPN_CONNECTION.TUNNEL.REMOTE_1TO1NAT
    WebUi Label: Network address for remote 1:1 NAT
    Network address for remote 1-to-1 NAT."
  ::= { mGuardVPNTunEntry 11 }

-- VPN_CONNECTION.TUNNEL.REMOTE_MASQ_IP
mGuardVPNTunRemoteMasq OBJECT-TYPE
  SYNTAX IpAddress
  ACCESS read-write
  STATUS mandatory
  DESCRIPTION
    "Variable name: VPN_CONNECTION.TUNNEL.REMOTE_MASQ_IP
    WebUi Label: Internal IP address used for remote masquerading
    Local IP used to masquerade remote addresses"
  ::= { mGuardVPNTunEntry 53 }

-- VPN_CONNECTION.TUNNEL.PROTOCOL
mGuardVPNTunProto OBJECT-TYPE
  SYNTAX INTEGER {
    icmp(1),
    tcp(6),
    udp(17),
    all(256)
  }
  ACCESS read-write
  STATUS mandatory
  DESCRIPTION
    "Variable name: VPN_CONNECTION.TUNNEL.PROTOCOL
    WebUi Label: Protocol
    Protocol for the VPN connection."
  ::= { mGuardVPNTunEntry 12 }

-- VPN_CONNECTION.TUNNEL.LOCAL_PORT
mGuardVPNTunLocalPort OBJECT-TYPE
  SYNTAX DisplayString
  ACCESS read-write
  STATUS mandatory
  DESCRIPTION
    "Variable name: VPN_CONNECTION.TUNNEL.LOCAL_PORT
    WebUi Label: Local Port ('%all' for all ports, a number between 1 and 65535 or
     '%any' to accept any proposal.)
    Local port when mGuardVPNTunProto is set to udp or tcp."
  ::= { mGuardVPNTunEntry 13 }

-- VPN_CONNECTION.TUNNEL.LOCAL_MASQ_NET
mGuardVPNTunLocalMasq OBJECT-TYPE
  SYNTAX DisplayString
  ACCESS read-write
  STATUS mandatory
  DESCRIPTION
    "Variable name: VPN_CONNECTION.TUNNEL.LOCAL_MASQ_NET
    WebUi Label: Internal network address for local masquerading
    Local IP for L2TP connections"
  ::= { mGuardVPNTunEntry 52 }

-- VPN_CONNECTION.TUNNEL.TYPE
mGuardVPNTunType OBJECT-TYPE
  SYNTAX INTEGER {
    tunnel(1),
    transport(2),
    modecfg(3)
  }
  ACCESS read-write
  STATUS mandatory
  DESCRIPTION
    "Variable name: VPN_CONNECTION.TUNNEL.TYPE
    WebUi Label: Type
    The type of the connection: tunnel: to connect networks (or hosts)
    transport: to connect hosts"
  ::= { mGuardVPNTunEntry 4 }

-- VPN_CONNECTION.TUNNEL.REMOTE_PORT
mGuardVPNTunRemotePort OBJECT-TYPE
  SYNTAX DisplayString
  ACCESS read-write
  STATUS mandatory
  DESCRIPTION
    "Variable name: VPN_CONNECTION.TUNNEL.REMOTE_PORT
    WebUi Label: Remote Port ('%all' for all ports, a number between 1 and 65535 or
     '%any' to accept any proposal.)
    Remote port when mGuardVPNTunProto is set to udp or tcp."
  ::= { mGuardVPNTunEntry 14 }

-- VPN_CONNECTION.TUNNEL.ENABLED
mGuardVPNTunEnable OBJECT-TYPE
  SYNTAX INTEGER {
    yes(1),
    no(2)
  }
  ACCESS read-write
  STATUS mandatory
  DESCRIPTION
    "Variable name: VPN_CONNECTION.TUNNEL.ENABLED
    WebUi Label: Enabled
    Whether this connection is enabled: yes / no."
  ::= { mGuardVPNTunEntry 3 }


-- VPN_CONNECTION.TUNNEL.LOCAL_N_TO_N_NAT table
mGuardVPNTunLocalNtoNNATTable OBJECT-TYPE
  SYNTAX SEQUENCE OF MGuardVPNTunLocalNtoNNATEntry
  ACCESS not-accessible
  STATUS mandatory
  DESCRIPTION
    "A table of VPN_CONNECTION.TUNNEL.LOCAL_N_TO_N_NAT"
  ::= { mGuardVPNTunnel 3 }

-- VPN_CONNECTION.TUNNEL.LOCAL_N_TO_N_NAT table entry
mGuardVPNTunLocalNtoNNATEntry OBJECT-TYPE
  SYNTAX MGuardVPNTunLocalNtoNNATEntry
  ACCESS not-accessible
  STATUS mandatory
  DESCRIPTION
    "An entry of VPN_CONNECTION.TUNNEL.LOCAL_N_TO_N_NAT"
  INDEX { mGuardVPNconIndex, mGuardVPNTunRuleIndex, mGuardVPNTunLocalNtoNNATIndex }
  ::= { mGuardVPNTunLocalNtoNNATTable 1 }

MGuardVPNTunLocalNtoNNATEntry ::= SEQUENCE {
  mGuardVPNTunLocalNtoNNATIndex            INTEGER,
  mGuardVPNTunLocalNtoNNATStatus           RowStatus,
  mGuardVPNTunLocal1to1NatComment          DisplayString,
  mGuardVPNTunLocal1to1NatFromNet          IpAddress,
  mGuardVPNTunLocal1to1NatMask             INTEGER,
  mGuardVPNTunLocal1to1NatToNet            IpAddress
}

-- VPN_CONNECTION.TUNNEL.LOCAL_N_TO_N_NAT table index
mGuardVPNTunLocalNtoNNATIndex OBJECT-TYPE
  SYNTAX INTEGER (1..2147483647)
  ACCESS not-accessible
  STATUS mandatory
  DESCRIPTION
    "Index to VPN_CONNECTION.TUNNEL.LOCAL_N_TO_N_NAT"
  ::= { mGuardVPNTunLocalNtoNNATEntry 1 }

-- VPN_CONNECTION.TUNNEL.LOCAL_N_TO_N_NAT row status
mGuardVPNTunLocalNtoNNATStatus OBJECT-TYPE
  SYNTAX RowStatus
  ACCESS read-write
  STATUS mandatory
  DESCRIPTION
    "RowStatus of VPN_CONNECTION.TUNNEL.LOCAL_N_TO_N_NAT"
  ::= { mGuardVPNTunLocalNtoNNATEntry 2 }

-- VPN_CONNECTION.TUNNEL.LOCAL_N_TO_N_NAT.COMMENT
mGuardVPNTunLocal1to1NatComment OBJECT-TYPE
  SYNTAX DisplayString
  ACCESS read-write
  STATUS mandatory
  DESCRIPTION
    "Variable name: VPN_CONNECTION.TUNNEL.LOCAL_N_TO_N_NAT.COMMENT
    WebUi Label: Comment
    Commentary or name for this mapping."
  ::= { mGuardVPNTunLocalNtoNNATEntry 3 }

-- VPN_CONNECTION.TUNNEL.LOCAL_N_TO_N_NAT.FROM_NET
mGuardVPNTunLocal1to1NatFromNet OBJECT-TYPE
  SYNTAX IpAddress
  ACCESS read-write
  STATUS mandatory
  DESCRIPTION
    "Variable name: VPN_CONNECTION.TUNNEL.LOCAL_N_TO_N_NAT.FROM_NET
    WebUi Label: Real network
    Source subnetwork for local 1-to-1 NAT."
  ::= { mGuardVPNTunLocalNtoNNATEntry 4 }

-- VPN_CONNECTION.TUNNEL.LOCAL_N_TO_N_NAT.MASK
mGuardVPNTunLocal1to1NatMask OBJECT-TYPE
  SYNTAX INTEGER(1..32)
  ACCESS read-write
  STATUS mandatory
  DESCRIPTION
    "Variable name: VPN_CONNECTION.TUNNEL.LOCAL_N_TO_N_NAT.MASK
    WebUi Label: Netmask
    Subnetwork mask for 1:1 NAT mapping."
  ::= { mGuardVPNTunLocalNtoNNATEntry 5 }

-- VPN_CONNECTION.TUNNEL.LOCAL_N_TO_N_NAT.TO_NET
mGuardVPNTunLocal1to1NatToNet OBJECT-TYPE
  SYNTAX IpAddress
  ACCESS read-write
  STATUS mandatory
  DESCRIPTION
    "Variable name: VPN_CONNECTION.TUNNEL.LOCAL_N_TO_N_NAT.TO_NET
    WebUi Label: Virtual network
    Target subnetwork for local 1-to-1 NAT."
  ::= { mGuardVPNTunLocalNtoNNATEntry 6 }

-- VPN_CONNECTION.TUNNEL.REMOTE_NAT
mGuardVPNTunRemoteNat OBJECT-TYPE
  SYNTAX INTEGER {
    none(1),
    use1to1nat(2),
    masq(3)
  }
  ACCESS read-write
  STATUS mandatory
  DESCRIPTION
    "Variable name: VPN_CONNECTION.TUNNEL.REMOTE_NAT
    WebUi Label: Remote NAT for IPsec tunnel connections
    Enable 1-to-1 NAT or masquerading of the remote network in router
    mode."
  ::= { mGuardVPNTunEntry 55 }

-- VPN_CONNECTION.TUNNEL.VIRTUAL_IP
mGuardVPNTunVirtIP OBJECT-TYPE
  SYNTAX IpAddress
  ACCESS read-write
  STATUS mandatory
  DESCRIPTION
    "Variable name: VPN_CONNECTION.TUNNEL.VIRTUAL_IP
    WebUi Label: The virtual IP which will be used by the client in Stealth mode
    The virtual IP for the peer to be used in stealth mode."
  ::= { mGuardVPNTunEntry 7 }

-- VPN_CONNECTION.TUNNEL.LOCAL_NAT
mGuardVPNTunLocalNat OBJECT-TYPE
  SYNTAX INTEGER {
    none(1),
    use1to1nat(2),
    masq(3)
  }
  ACCESS read-write
  STATUS mandatory
  DESCRIPTION
    "Variable name: VPN_CONNECTION.TUNNEL.LOCAL_NAT
    WebUi Label: Local NAT for IPsec tunnel connections
    Enable 1-to-1 NAT or masquerading of the local network in router mode."
  ::= { mGuardVPNTunEntry 54 }

-- VPN_CONNECTION.TUNNEL.REMOTE
mGuardVPNTunRemote OBJECT-TYPE
  SYNTAX DisplayString
  ACCESS read-write
  STATUS mandatory
  DESCRIPTION
    "Variable name: VPN_CONNECTION.TUNNEL.REMOTE
    WebUi Label: Remote
    Remote network for tunnel connection in CIDR notation."
  ::= { mGuardVPNTunEntry 6 }

-- VPN_CONNECTION.TUNNEL.LOCAL
mGuardVPNTunLocal OBJECT-TYPE
  SYNTAX DisplayString
  ACCESS read-write
  STATUS mandatory
  DESCRIPTION
    "Variable name: VPN_CONNECTION.TUNNEL.LOCAL
    WebUi Label: Local
    Local network for tunnel connection in CIDR notation."
  ::= { mGuardVPNTunEntry 5 }

-- VPN_CONNECTION.TUNNEL.DUMMY_ROUTE
mGuardVPNTunDummyRoute OBJECT-TYPE
  SYNTAX INTEGER {
    yes(1),
    no(2)
  }
  ACCESS read-write
  STATUS mandatory
  DESCRIPTION
    "Variable name: VPN_CONNECTION.TUNNEL.DUMMY_ROUTE
    WebUi Label: Add kernel route to remote net to allow OSPF route redistribution
    Introduce the remote net of the IPsec tunnel as interface route to the
    dummy device. This makes it possible to propagate the IPsec remote net
    via dynamic routing."
  ::= { mGuardVPNTunEntry 15 }

-- VPN_CONNECTION.AGGRESSIVE
mGuardVPNAggressive OBJECT-TYPE
  SYNTAX INTEGER {
    no(1),
    yes(2)
  }
  ACCESS read-write
  STATUS mandatory
  DESCRIPTION
    "Variable name: VPN_CONNECTION.AGGRESSIVE
    WebUi Label: ISAKMP mode (Please note that 'Aggressive Mode' is vulnerable to
     attacks.)
    Whether to use/accept aggressive mode VPN connections for this one."
  ::= { mGuardVPNConnectionEntry 43 }

-- VPN_CONNECTION.MODECFG_SERVER_REMOTE
mGuardVPNconModeCfgServerRemote OBJECT-TYPE
  SYNTAX INTEGER {
    pool(1),
    isplitinc-static(2),
    isplitinc-seccloud(3)
  }
  ACCESS read-write
  STATUS mandatory
  DESCRIPTION
    "Variable name: VPN_CONNECTION.MODECFG_SERVER_REMOTE
    WebUi Label: Remote
    MODECFG server mode: Configures whether the server's remote network
    shall be taken from the pool, a statically configured split network
    setup or shall be obtained dynamically in a secure cloud scenario.
    This option implicitly enables sending Innominate enhanced lists if
    the client supports this feature as well."
  ::= { mGuardVPNConnectionEntry 78 }

-- VPN_CONNECTION.PROTO_AH
mGuardVPNProtoAH OBJECT-TYPE
  SYNTAX INTEGER {
    yes(1),
    no(2)
  }
  ACCESS read-write
  STATUS mandatory
  DESCRIPTION
    "Variable name: VPN_CONNECTION.PROTO_AH
    WebUi Label: --
    Use the AH protocol. Only 'no' is supported."
  ::= { mGuardVPNConnectionEntry 26 }

-- VPN_CONNECTION.VPN_PFS
mGuardVPNpfs OBJECT-TYPE
  SYNTAX INTEGER {
    no(1),
    all(2),
    modp1024(3),
    modp1536(4),
    modp2048(5),
    modp3072(6),
    modp4096(7),
    modp6144(8),
    modp8192(9)
  }
  ACCESS read-write
  STATUS mandatory
  DESCRIPTION
    "Variable name: VPN_CONNECTION.VPN_PFS
    WebUi Label: Perfect Forward Secrecy (PFS) (Activation recommended. The remote site
     must have the same entry.)
    IPsec perfect forward secrecy: no / all / modp1024 / modp1536 /
    modp2048 / modp3072 / modp4096 / modp6144 / modp8192"
  ::= { mGuardVPNConnectionEntry 18 }

-- VPN_CONNECTION.CONTROL
mGuardVPNconControl OBJECT-TYPE
  SYNTAX DisplayString
  ACCESS read-write
  STATUS mandatory
  DESCRIPTION
    "Variable name: VPN_CONNECTION.CONTROL
    WebUi Label: Controlling service input
    Write 'cmd1', 'cmd2' or 'cmd3' to this object to control this VPN
    connection with a command switch. Write 'none' to disable this
    feature."
  ::= { mGuardVPNConnectionEntry 69 }


-- VPN_CONNECTION.VPN_IPSEC_PREF table
mGuardVPNIPsecPrefTable OBJECT-TYPE
  SYNTAX SEQUENCE OF MGuardVPNIPsecPrefEntry
  ACCESS not-accessible
  STATUS mandatory
  DESCRIPTION
    "A table of VPN_CONNECTION.VPN_IPSEC_PREF"
  ::= { mGuardVPNIPsecPref 1 }

-- VPN_CONNECTION.VPN_IPSEC_PREF table entry
mGuardVPNIPsecPrefEntry OBJECT-TYPE
  SYNTAX MGuardVPNIPsecPrefEntry
  ACCESS not-accessible
  STATUS mandatory
  DESCRIPTION
    "An entry of VPN_CONNECTION.VPN_IPSEC_PREF"
  INDEX { mGuardVPNconIndex, mGuardVPNIPsecPrefIndex }
  ::= { mGuardVPNIPsecPrefTable 1 }

MGuardVPNIPsecPrefEntry ::= SEQUENCE {
  mGuardVPNIPsecPrefIndex                  INTEGER,
  mGuardVPNIPsecPrefRowStatus              RowStatus,
  mGuardVPNIPsecPrefAlg                    INTEGER,
  mGuardVPNIPsecPrefHash                   INTEGER
}

-- VPN_CONNECTION.VPN_IPSEC_PREF table index
mGuardVPNIPsecPrefIndex OBJECT-TYPE
  SYNTAX INTEGER (1..2147483647)
  ACCESS not-accessible
  STATUS mandatory
  DESCRIPTION
    "Index to VPN_CONNECTION.VPN_IPSEC_PREF"
  ::= { mGuardVPNIPsecPrefEntry 1 }

-- VPN_CONNECTION.VPN_IPSEC_PREF row status
mGuardVPNIPsecPrefRowStatus OBJECT-TYPE
  SYNTAX RowStatus
  ACCESS read-write
  STATUS mandatory
  DESCRIPTION
    "RowStatus of VPN_CONNECTION.VPN_IPSEC_PREF"
  ::= { mGuardVPNIPsecPrefEntry 2 }

-- VPN_CONNECTION.VPN_IPSEC_PREF.ALG
mGuardVPNIPsecPrefAlg OBJECT-TYPE
  SYNTAX INTEGER {
    des(1),
    tripledes168(2),
    aes128(3),
    aes192(4),
    aes256(5),
    null(6),
    proprietaryA(7),
    proprietaryB(8),
    aesc(9)
  }
  ACCESS read-write
  STATUS mandatory
  DESCRIPTION
    "Variable name: VPN_CONNECTION.VPN_IPSEC_PREF.ALG
    WebUi Label: Encryption
    IPsec encryption algorithm: des / 3des168 / aes128 / aes192 / aes256 /
    null / proprietary_a / proprietary_b / aesc"
  ::= { mGuardVPNIPsecPrefEntry 3 }

-- VPN_CONNECTION.VPN_IPSEC_PREF.HASH
mGuardVPNIPsecPrefHash OBJECT-TYPE
  SYNTAX INTEGER {
    all(1),
    md5(2),
    sha1(3),
    sha2-256(5),
    sha2-384(6),
    sha2-512(7)
  }
  ACCESS read-write
  STATUS mandatory
  DESCRIPTION
    "Variable name: VPN_CONNECTION.VPN_IPSEC_PREF.HASH
    WebUi Label: Hash
    IPsec SA hash algorithm: all / md5 / sha1 / sha2-256 / sha2-512"
  ::= { mGuardVPNIPsecPrefEntry 4 }

-- VPN_CONNECTION.IPSEC_REKEYMARGIN_BYTES
mGuardVPNRekeyMarginBytes OBJECT-TYPE
  SYNTAX INTEGER(0..2147483647)
  ACCESS read-write
  STATUS mandatory
  DESCRIPTION
    "Variable name: VPN_CONNECTION.IPSEC_REKEYMARGIN_BYTES
    WebUi Label: Re-key margin for the traffic limit (applies to IPsec SAs only)
    Specifies the re-key margin in bytes for an IPsec SA of this VPN
    connection. Acceptable range is from 0 to 2147483647 bytes. The value
    zero disables the limit."
  ::= { mGuardVPNConnectionEntry 62 }

-- VPN_CONNECTION.MODECFG_CLIENT_REMOTE
mGuardVPNconModeCfgClientRemote OBJECT-TYPE
  SYNTAX INTEGER {
    fixed(1),
    splitinc(2)
  }
  ACCESS read-write
  STATUS mandatory
  DESCRIPTION
    "Variable name: VPN_CONNECTION.MODECFG_CLIENT_REMOTE
    WebUi Label: Remote
    MODECFG client mode: Configures whether the client's remote network
    shall allow split network configuration."
  ::= { mGuardVPNConnectionEntry 79 }

-- VPN_CONNECTION.VPN_PSK
mGuardVPNpsk OBJECT-TYPE
  SYNTAX DisplayString
  ACCESS read-write
  STATUS mandatory
  DESCRIPTION
    "Variable name: VPN_CONNECTION.VPN_PSK
    WebUi Label: Pre-shared key (PSK)
    The Pre-Shared Secret to be used when mGuardVPNauthType is set to psk."
  ::= { mGuardVPNConnectionEntry 11 }


-- VPN_CONNECTION.VPN_IKE_PREF table
mGuardVPNIkePrefTable OBJECT-TYPE
  SYNTAX SEQUENCE OF MGuardVPNIkePrefEntry
  ACCESS not-accessible
  STATUS mandatory
  DESCRIPTION
    "A table of VPN_CONNECTION.VPN_IKE_PREF"
  ::= { mGuardVPNIkePref 1 }

-- VPN_CONNECTION.VPN_IKE_PREF table entry
mGuardVPNIkePrefEntry OBJECT-TYPE
  SYNTAX MGuardVPNIkePrefEntry
  ACCESS not-accessible
  STATUS mandatory
  DESCRIPTION
    "An entry of VPN_CONNECTION.VPN_IKE_PREF"
  INDEX { mGuardVPNconIndex, mGuardVPNIkePrefIndex }
  ::= { mGuardVPNIkePrefTable 1 }

MGuardVPNIkePrefEntry ::= SEQUENCE {
  mGuardVPNIkePrefIndex                    INTEGER,
  mGuardVPNIkePrefRowStatus                RowStatus,
  mGuardVPNIkePrefAlg                      INTEGER,
  mGuardVPNIkePrefHash                     INTEGER,
  mGuardVPNIkePrefDH                       INTEGER
}

-- VPN_CONNECTION.VPN_IKE_PREF table index
mGuardVPNIkePrefIndex OBJECT-TYPE
  SYNTAX INTEGER (1..2147483647)
  ACCESS not-accessible
  STATUS mandatory
  DESCRIPTION
    "Index to VPN_CONNECTION.VPN_IKE_PREF"
  ::= { mGuardVPNIkePrefEntry 1 }

-- VPN_CONNECTION.VPN_IKE_PREF row status
mGuardVPNIkePrefRowStatus OBJECT-TYPE
  SYNTAX RowStatus
  ACCESS read-write
  STATUS mandatory
  DESCRIPTION
    "RowStatus of VPN_CONNECTION.VPN_IKE_PREF"
  ::= { mGuardVPNIkePrefEntry 2 }

-- VPN_CONNECTION.VPN_IKE_PREF.ALG
mGuardVPNIkePrefAlg OBJECT-TYPE
  SYNTAX INTEGER {
    des(1),
    tripledes168(2),
    aes128(3),
    aes192(4),
    aes256(5),
    proprietaryA(7),
    proprietaryB(8)
  }
  ACCESS read-write
  STATUS mandatory
  DESCRIPTION
    "Variable name: VPN_CONNECTION.VPN_IKE_PREF.ALG
    WebUi Label: Encryption
    ISAKMP SA encryption algorithm: des / 3des168 / aes128 / aes192 /
    aes256"
  ::= { mGuardVPNIkePrefEntry 3 }

-- VPN_CONNECTION.VPN_IKE_PREF.HASH
mGuardVPNIkePrefHash OBJECT-TYPE
  SYNTAX INTEGER {
    all(1),
    md5(2),
    sha1(3),
    sha2-256(5),
    sha2-384(6),
    sha2-512(7)
  }
  ACCESS read-write
  STATUS mandatory
  DESCRIPTION
    "Variable name: VPN_CONNECTION.VPN_IKE_PREF.HASH
    WebUi Label: Hash
    ISAKMP SA hash algorithm: all / md5 / sha1 / sha2-256 / sha2-512"
  ::= { mGuardVPNIkePrefEntry 4 }

-- VPN_CONNECTION.VPN_IKE_PREF.DH
mGuardVPNIkePrefDH OBJECT-TYPE
  SYNTAX INTEGER {
    all(1),
    modp1024(2),
    modp1536(3),
    modp2048(4),
    modp3072(5),
    modp4096(6),
    modp6144(7),
    modp8192(8)
  }
  ACCESS read-write
  STATUS mandatory
  DESCRIPTION
    "Variable name: VPN_CONNECTION.VPN_IKE_PREF.DH
    WebUi Label: Diffie-Hellman
    ISAKMP DH group: modp1024 (aka group 1) / modp1536 (aka group 5) /
    modp2048 / modp3072 / modp4096"
  ::= { mGuardVPNIkePrefEntry 5 }

-- VPN_CONNECTION.FW_OUTGOING_GLOBAL
mGuardVPNFwOutGlobal OBJECT-TYPE
  SYNTAX INTEGER {
    accept(1),
    drop(2),
    rules(3),
    ping(4)
  }
  ACCESS read-write
  STATUS mandatory
  DESCRIPTION
    "Variable name: VPN_CONNECTION.FW_OUTGOING_GLOBAL
    WebUi Label: General firewall setting
    Global switch to accept or drop all outgoing connections or to follow
    the explicit firewall rules"
  ::= { mGuardVPNConnectionEntry 65 }

-- VPN_CONNECTION.MODECFG_WINS1
mGuardVPNconModeCfgWINS1 OBJECT-TYPE
  SYNTAX IpAddress
  ACCESS read-write
  STATUS mandatory
  DESCRIPTION
    "Variable name: VPN_CONNECTION.MODECFG_WINS1
    WebUi Label: 1st WINS server for the peer
    MODECFG server mode: The address of the first WINS server announced to
    the client."
  ::= { mGuardVPNConnectionEntry 75 }

-- VPN_CONNECTION.VPN_START
mGuardVPNconStart OBJECT-TYPE
  SYNTAX INTEGER {
    disabled(1),
    stopped(2),
    started(3)
  }
  ACCESS read-write
  STATUS mandatory
  DESCRIPTION
    "Variable name: VPN_CONNECTION.VPN_START
    WebUi Label: Initial mode
    Disable the connection completely or set the initial mode."
  ::= { mGuardVPNConnectionEntry 67 }


-- VPN_CONNECTION.MODECFG_SERVER_LOCAL_NETWORKS table
mGuardVPNModeCfgServerLocTable OBJECT-TYPE
  SYNTAX SEQUENCE OF MGuardVPNModeCfgServerLocEntry
  ACCESS not-accessible
  STATUS mandatory
  DESCRIPTION
    "A table of VPN_CONNECTION.MODECFG_SERVER_LOCAL_NETWORKS"
  ::= { mGuardVPNModeCfgServerLocNets 1 }

-- VPN_CONNECTION.MODECFG_SERVER_LOCAL_NETWORKS table entry
mGuardVPNModeCfgServerLocEntry OBJECT-TYPE
  SYNTAX MGuardVPNModeCfgServerLocEntry
  ACCESS not-accessible
  STATUS mandatory
  DESCRIPTION
    "An entry of VPN_CONNECTION.MODECFG_SERVER_LOCAL_NETWORKS"
  INDEX { mGuardVPNconIndex, mGuardVPNModeCfgServerLocIndex }
  ::= { mGuardVPNModeCfgServerLocTable 1 }

MGuardVPNModeCfgServerLocEntry ::= SEQUENCE {
  mGuardVPNModeCfgServerLocIndex           INTEGER,
  mGuardVPNModeCfgServerLocRowStatus       RowStatus,
  mGuardVPNModeCfgServerLocNet             DisplayString
}

-- VPN_CONNECTION.MODECFG_SERVER_LOCAL_NETWORKS table index
mGuardVPNModeCfgServerLocIndex OBJECT-TYPE
  SYNTAX INTEGER (1..2147483647)
  ACCESS not-accessible
  STATUS mandatory
  DESCRIPTION
    "Index to VPN_CONNECTION.MODECFG_SERVER_LOCAL_NETWORKS"
  ::= { mGuardVPNModeCfgServerLocEntry 1 }

-- VPN_CONNECTION.MODECFG_SERVER_LOCAL_NETWORKS row status
mGuardVPNModeCfgServerLocRowStatus OBJECT-TYPE
  SYNTAX RowStatus
  ACCESS read-write
  STATUS mandatory
  DESCRIPTION
    "RowStatus of VPN_CONNECTION.MODECFG_SERVER_LOCAL_NETWORKS"
  ::= { mGuardVPNModeCfgServerLocEntry 2 }

-- VPN_CONNECTION.MODECFG_SERVER_LOCAL_NETWORKS.NETWORK
mGuardVPNModeCfgServerLocNet OBJECT-TYPE
  SYNTAX DisplayString
  ACCESS read-write
  STATUS mandatory
  DESCRIPTION
    "Variable name: VPN_CONNECTION.MODECFG_SERVER_LOCAL_NETWORKS.NETWORK
    WebUi Label: Network
    The network in CIDR notation."
  ::= { mGuardVPNModeCfgServerLocEntry 3 }

-- VPN_CONNECTION.REKEYMARGIN
mGuardVPNRekeyMargin OBJECT-TYPE
  SYNTAX INTEGER
  ACCESS read-write
  STATUS mandatory
  DESCRIPTION
    "Variable name: VPN_CONNECTION.REKEYMARGIN
    WebUi Label: Re-key margin for lifetimes (applies to ISAKMP SAs and IPsec SAs)
    Rekey margin in seconds."
  ::= { mGuardVPNConnectionEntry 35 }

-- VPN_CONNECTION.PROTO_ESP
mGuardVPNProtoESP OBJECT-TYPE
  SYNTAX INTEGER {
    yes(1),
    no(2)
  }
  ACCESS read-write
  STATUS mandatory
  DESCRIPTION
    "Variable name: VPN_CONNECTION.PROTO_ESP
    WebUi Label: --
    Use the ESP protocol. Only 'yes' is supported."
  ::= { mGuardVPNConnectionEntry 27 }

-- VPN_CONNECTION.IKELIFETIME
mGuardVPNIkeLifetime OBJECT-TYPE
  SYNTAX INTEGER(1..86400)
  ACCESS read-write
  STATUS mandatory
  DESCRIPTION
    "Variable name: VPN_CONNECTION.IKELIFETIME
    WebUi Label: ISAKMP SA lifetime
    ISAKMP SA lifetime in seconds."
  ::= { mGuardVPNConnectionEntry 33 }

-- VPN_CONNECTION.REPLAYWINDOW
mGuardVPNReplayWindow OBJECT-TYPE
  SYNTAX INTEGER(0..64)
  ACCESS read-write
  STATUS mandatory
  DESCRIPTION
    "Variable name: VPN_CONNECTION.REPLAYWINDOW
    WebUi Label: Replay window
    Size of the Replay window (0-64)"
  ::= { mGuardVPNConnectionEntry 47 }

-- VPN_CONNECTION.PROTO_COMP
mGuardVPNComp OBJECT-TYPE
  SYNTAX INTEGER {
    yes(1),
    no(2)
  }
  ACCESS read-write
  STATUS mandatory
  DESCRIPTION
    "Variable name: VPN_CONNECTION.PROTO_COMP
    WebUi Label: Use compression
    Use IPsec compression. Only 'no' is supported."
  ::= { mGuardVPNConnectionEntry 28 }

-- VPN_CONNECTION.FW_INCOMING_GLOBAL
mGuardVPNFwInGlobal OBJECT-TYPE
  SYNTAX INTEGER {
    accept(1),
    drop(2),
    rules(3),
    ping(4)
  }
  ACCESS read-write
  STATUS mandatory
  DESCRIPTION
    "Variable name: VPN_CONNECTION.FW_INCOMING_GLOBAL
    WebUi Label: General firewall setting
    Global switch to accept or drop all incoming connections or to follow
    the explicit firewall rules"
  ::= { mGuardVPNConnectionEntry 64 }

-- VPN_CONNECTION.KEYINGTRIES
mGuardVPNKeyingTries OBJECT-TYPE
  SYNTAX INTEGER
  ACCESS read-write
  STATUS mandatory
  DESCRIPTION
    "Variable name: VPN_CONNECTION.KEYINGTRIES
    WebUi Label: Keying tries (0 means unlimited tries)
    Rekey fuzz (in percent)."
  ::= { mGuardVPNConnectionEntry 37 }

-- VPN_CONNECTION.MODECFG_DNS2
mGuardVPNconModeCfgDNS2 OBJECT-TYPE
  SYNTAX IpAddress
  ACCESS read-write
  STATUS mandatory
  DESCRIPTION
    "Variable name: VPN_CONNECTION.MODECFG_DNS2
    WebUi Label: 2nd DNS server for the peer
    MODECFG server mode: The address of the second DNS server announced to
    the client."
  ::= { mGuardVPNConnectionEntry 74 }

-- VPN_CONNECTION.MODECFG_WINS2
mGuardVPNconModeCfgWINS2 OBJECT-TYPE
  SYNTAX IpAddress
  ACCESS read-write
  STATUS mandatory
  DESCRIPTION
    "Variable name: VPN_CONNECTION.MODECFG_WINS2
    WebUi Label: 2nd WINS server for the peer
    MODECFG server mode: The address of the second WINS server announced
    to the client."
  ::= { mGuardVPNConnectionEntry 76 }

-- VPN_CONNECTION.MODECFG_SERVER_LOCAL
mGuardVPNconModeCfgServerLocal OBJECT-TYPE
  SYNTAX INTEGER {
    fixed(1),
    splitinc-static(2),
    splitinc-seccloud(3)
  }
  ACCESS read-write
  STATUS mandatory
  DESCRIPTION
    "Variable name: VPN_CONNECTION.MODECFG_SERVER_LOCAL
    WebUi Label: Local
    MODECFG server mode: Configures whether the server's local network
    shall be fixed, a statically configured split network setup or shall
    be obtained dynamically in a secure cloud scenario."
  ::= { mGuardVPNConnectionEntry 77 }

-- VPN_CONNECTION.FORCE_UDP_ENCAPS
mGuardVPNForceUDP OBJECT-TYPE
  SYNTAX INTEGER {
    yes(1),
    no(2)
  }
  ACCESS read-write
  STATUS mandatory
  DESCRIPTION
    "Variable name: VPN_CONNECTION.FORCE_UDP_ENCAPS
    WebUi Label: Enforce NAT-T UDP encapsulation
    Always use UDP encapsulation for IKE and ESP."
  ::= { mGuardVPNConnectionEntry 51 }

-- VPN_CONNECTION.VPN_GW
mGuardVPNremGW OBJECT-TYPE
  SYNTAX DisplayString
  ACCESS read-write
  STATUS mandatory
  DESCRIPTION
    "Variable name: VPN_CONNECTION.VPN_GW
    WebUi Label: Address of the remote site's VPN gateway (IP address, hostname, or
     '%any' for any IP, multiple clients or clients behind a NAT gateway)
    Remote VPN gateway."
  ::= { mGuardVPNConnectionEntry 4 }

-- VPN_CONNECTION.MODECFG_XAUTH_MODE
mGuardVPNconModeCfgXauth OBJECT-TYPE
  SYNTAX INTEGER {
    off(1),
    server(2),
    client(3)
  }
  ACCESS read-write
  STATUS mandatory
  DESCRIPTION
    "Variable name: VPN_CONNECTION.MODECFG_XAUTH_MODE
    WebUi Label: Mode configuration
    Configures whether this connection shall support MODECFG/XAUTH and
    whether to be in server or in client mode."
  ::= { mGuardVPNConnectionEntry 71 }

-- VPN_CONNECTION.IKEPORT
mGuardVPNRemoteIKEPort OBJECT-TYPE
  SYNTAX INTEGER(1..65535)
  ACCESS read-write
  STATUS mandatory
  DESCRIPTION
    "Variable name: VPN_CONNECTION.IKEPORT
    WebUi Label: Remote site's IKE port
    The UDP port of the remote IKE daemon. The default is 500."
  ::= { mGuardVPNConnectionEntry 50 }

-- VPN_CONNECTION.FW_OUTGOING
mGuardVPNFWOUTuuid OBJECT-TYPE
  SYNTAX DisplayString
  ACCESS read-only
  STATUS mandatory
  DESCRIPTION
    "Variable name: VPN_CONNECTION.FW_OUTGOING
    WebUi Label: --
    Universally Unique Identifier (UUID, RFC 4122) used for
    mGuardVPNFWOUTTable logging."
  ::= { mGuardVPNConnectionEntry 82 }


-- VPN_CONNECTION.FW_OUTGOING table
mGuardVPNFWOUTTable OBJECT-TYPE
  SYNTAX SEQUENCE OF MGuardVPNFWOUTEntry
  ACCESS not-accessible
  STATUS mandatory
  DESCRIPTION
    "A table of VPN_CONNECTION.FW_OUTGOING"
  ::= { mGuardVPNFW 2 }

-- VPN_CONNECTION.FW_OUTGOING table entry
mGuardVPNFWOUTEntry OBJECT-TYPE
  SYNTAX MGuardVPNFWOUTEntry
  ACCESS not-accessible
  STATUS mandatory
  DESCRIPTION
    "An entry of VPN_CONNECTION.FW_OUTGOING"
  INDEX { mGuardVPNconIndex, mGuardVPNFWOUTruleIndex }
  ::= { mGuardVPNFWOUTTable 1 }

MGuardVPNFWOUTEntry ::= SEQUENCE {
  mGuardVPNFWOUTruleIndex                  INTEGER,
  mGuardVPNFWOUTproto                      INTEGER,
  mGuardVPNFWOUTlog                        INTEGER,
  mGuardVPNFWOUTRowStatus                  RowStatus,
  mGuardVPNFWOUTcomment                    DisplayString,
  mGuardVPNFWOUTtargetRef                  OBJECT IDENTIFIER,
  mGuardVPNFWOUTtargetValue                INTEGER,
  mGuardVPNFWOUTsourceIPOrGroupValue       DisplayString,
  mGuardVPNFWOUTsourceIPOrGroupRef         OBJECT IDENTIFIER,
  mGuardVPNFWOUTdestinationIPOrGroupValue  DisplayString,
  mGuardVPNFWOUTdestinationIPOrGroupRef    OBJECT IDENTIFIER,
  mGuardVPNFWOUTsportOrGroupValue          DisplayString,
  mGuardVPNFWOUTsportOrGroupRef            OBJECT IDENTIFIER,
  mGuardVPNFWOUTdportOrGroupValue          DisplayString,
  mGuardVPNFWOUTdportOrGroupRef            OBJECT IDENTIFIER
}

-- VPN_CONNECTION.FW_OUTGOING table index
mGuardVPNFWOUTruleIndex OBJECT-TYPE
  SYNTAX INTEGER (1..2147483647)
  ACCESS not-accessible
  STATUS mandatory
  DESCRIPTION
    "Index to VPN_CONNECTION.FW_OUTGOING"
  ::= { mGuardVPNFWOUTEntry 2 }

-- VPN_CONNECTION.FW_OUTGOING row status
mGuardVPNFWOUTRowStatus OBJECT-TYPE
  SYNTAX RowStatus
  ACCESS read-write
  STATUS mandatory
  DESCRIPTION
    "RowStatus of VPN_CONNECTION.FW_OUTGOING"
  ::= { mGuardVPNFWOUTEntry 10 }

-- VPN_CONNECTION.FW_OUTGOING.COMMENT
mGuardVPNFWOUTcomment OBJECT-TYPE
  SYNTAX DisplayString
  ACCESS read-write
  STATUS mandatory
  DESCRIPTION
    "Variable name: VPN_CONNECTION.FW_OUTGOING.COMMENT
    WebUi Label: Comment
    Commentary or name for this rule."
  ::= { mGuardVPNFWOUTEntry 11 }

-- VPN_CONNECTION.FW_OUTGOING.FROM_PORT
mGuardVPNFWOUTsportOrGroupValue OBJECT-TYPE
  SYNTAX DisplayString
  ACCESS read-write
  STATUS mandatory
  DESCRIPTION
    "Variable name: VPN_CONNECTION.FW_OUTGOING.FROM_PORT
    WebUi Label: From port
    The rule's source port"
  ::= { mGuardVPNFWOUTEntry 20 }

-- VPN_CONNECTION.FW_OUTGOING.FROM_PORT reference
mGuardVPNFWOUTsportOrGroupRef OBJECT-TYPE
  SYNTAX OBJECT IDENTIFIER
  ACCESS read-write
  STATUS mandatory
  DESCRIPTION
    "Variable name: VPN_CONNECTION.FW_OUTGOING.FROM_PORT
    WebUi Label: From port
    The rule's source port as reference to port group"
  ::= { mGuardVPNFWOUTEntry 21 }

-- VPN_CONNECTION.FW_OUTGOING.LOG
mGuardVPNFWOUTlog OBJECT-TYPE
  SYNTAX INTEGER {
    yes(1),
    no(2)
  }
  ACCESS read-write
  STATUS mandatory
  DESCRIPTION
    "Variable name: VPN_CONNECTION.FW_OUTGOING.LOG
    WebUi Label: Log
    Log packets matching this rule."
  ::= { mGuardVPNFWOUTEntry 9 }

-- VPN_CONNECTION.FW_OUTGOING.PROTO
mGuardVPNFWOUTproto OBJECT-TYPE
  SYNTAX INTEGER {
    tcp(1),
    udp(2),
    icmp(3),
    all(4),
    gre(5)
  }
  ACCESS read-write
  STATUS mandatory
  DESCRIPTION
    "Variable name: VPN_CONNECTION.FW_OUTGOING.PROTO
    WebUi Label: Protocol
    The rule's transport protocol"
  ::= { mGuardVPNFWOUTEntry 8 }

-- VPN_CONNECTION.FW_OUTGOING.FROM_IP
mGuardVPNFWOUTsourceIPOrGroupValue OBJECT-TYPE
  SYNTAX DisplayString
  ACCESS read-write
  STATUS mandatory
  DESCRIPTION
    "Variable name: VPN_CONNECTION.FW_OUTGOING.FROM_IP
    WebUi Label: From IP
    The rule's source IP address"
  ::= { mGuardVPNFWOUTEntry 16 }

-- VPN_CONNECTION.FW_OUTGOING.FROM_IP reference
mGuardVPNFWOUTsourceIPOrGroupRef OBJECT-TYPE
  SYNTAX OBJECT IDENTIFIER
  ACCESS read-write
  STATUS mandatory
  DESCRIPTION
    "Variable name: VPN_CONNECTION.FW_OUTGOING.FROM_IP
    WebUi Label: From IP
    The rule's source IP address as reference to IP group"
  ::= { mGuardVPNFWOUTEntry 17 }

-- VPN_CONNECTION.FW_OUTGOING.IN_IP
mGuardVPNFWOUTdestinationIPOrGroupValue OBJECT-TYPE
  SYNTAX DisplayString
  ACCESS read-write
  STATUS mandatory
  DESCRIPTION
    "Variable name: VPN_CONNECTION.FW_OUTGOING.IN_IP
    WebUi Label: To IP
    The rule's destination IP address"
  ::= { mGuardVPNFWOUTEntry 18 }

-- VPN_CONNECTION.FW_OUTGOING.IN_IP reference
mGuardVPNFWOUTdestinationIPOrGroupRef OBJECT-TYPE
  SYNTAX OBJECT IDENTIFIER
  ACCESS read-write
  STATUS mandatory
  DESCRIPTION
    "Variable name: VPN_CONNECTION.FW_OUTGOING.IN_IP
    WebUi Label: To IP
    The rule's destination IP address as reference to IP group"
  ::= { mGuardVPNFWOUTEntry 19 }

-- VPN_CONNECTION.FW_OUTGOING.TARGET_REF
mGuardVPNFWOUTtargetValue OBJECT-TYPE
  SYNTAX INTEGER {
    accept(1),
    reject(2),
    drop(3)
  }
  ACCESS read-write
  STATUS mandatory
  DESCRIPTION
    "Variable name: VPN_CONNECTION.FW_OUTGOING.TARGET_REF
    WebUi Label: Action
    The rule's target. This object is effective if and only if the
    'mGuardVPNFWOUTtargetRef' object contains the OID of this object."
  ::= { mGuardVPNFWOUTEntry 13 }

-- VPN_CONNECTION.FW_OUTGOING.TARGET_REF reference
mGuardVPNFWOUTtargetRef OBJECT-TYPE
  SYNTAX OBJECT IDENTIFIER
  ACCESS read-write
  STATUS mandatory
  DESCRIPTION
    "Variable name: VPN_CONNECTION.FW_OUTGOING.TARGET_REF
    WebUi Label: Action
    Set this object to the OID of an 'mGuardFWRuleIndex' to select a
    firewall ruleset as this rule's target. Set this object to the OID of
    the 'mGuardVPNFWOUTtargetValue' object to choose a target from that
    objects range."
  ::= { mGuardVPNFWOUTEntry 12 }

-- VPN_CONNECTION.FW_OUTGOING.IN_PORT
mGuardVPNFWOUTdportOrGroupValue OBJECT-TYPE
  SYNTAX DisplayString
  ACCESS read-write
  STATUS mandatory
  DESCRIPTION
    "Variable name: VPN_CONNECTION.FW_OUTGOING.IN_PORT
    WebUi Label: To port
    The rule's destination port"
  ::= { mGuardVPNFWOUTEntry 22 }

-- VPN_CONNECTION.FW_OUTGOING.IN_PORT reference
mGuardVPNFWOUTdportOrGroupRef OBJECT-TYPE
  SYNTAX OBJECT IDENTIFIER
  ACCESS read-write
  STATUS mandatory
  DESCRIPTION
    "Variable name: VPN_CONNECTION.FW_OUTGOING.IN_PORT
    WebUi Label: To port
    The rule's destination port as reference to port group"
  ::= { mGuardVPNFWOUTEntry 23 }

-- VPN_CONNECTION.LOCAL_ID
mGuardVPNLocalID OBJECT-TYPE
  SYNTAX DisplayString
  ACCESS read-write
  STATUS mandatory
  DESCRIPTION
    "Variable name: VPN_CONNECTION.LOCAL_ID
    WebUi Label: Local
    Local ID."
  ::= { mGuardVPNConnectionEntry 30 }

-- VPN_CONNECTION.LOG_DEFAULT_OUTGOING
mGuardVPNFWLogDefOut OBJECT-TYPE
  SYNTAX INTEGER {
    yes(1),
    no(2)
  }
  ACCESS read-write
  STATUS mandatory
  DESCRIPTION
    "Variable name: VPN_CONNECTION.LOG_DEFAULT_OUTGOING
    WebUi Label: Log entries for unknown connection attempts
    Log entries for undefined outgoing connection attempts?"
  ::= { mGuardVPNConnectionEntry 23 }

-- VPN_CONNECTION.SMS_TOKEN
mGuardVPNconSmsToken OBJECT-TYPE
  SYNTAX DisplayString
  ACCESS read-write
  STATUS mandatory
  DESCRIPTION
    "Variable name: VPN_CONNECTION.SMS_TOKEN
    WebUi Label: Token for text message trigger
    Define a token to disable/enable the VPN connection per SMS."
  ::= { mGuardVPNConnectionEntry 68 }

-- VPN_CONNECTION.DPD_DELAY
mGuardVPNDPDDelay OBJECT-TYPE
  SYNTAX INTEGER
  ACCESS read-write
  STATUS mandatory
  DESCRIPTION
    "Variable name: VPN_CONNECTION.DPD_DELAY
    WebUi Label: Delay between requests for a sign of life
    Interval in seconds to wait before sending DPD requests when the
    remote end didn't send data. The default value is 30."
  ::= { mGuardVPNConnectionEntry 40 }

-- VPN_CONNECTION.LOCAL_CERT_REF
mGuardVPNLocalCertNewValue OBJECT-TYPE
  SYNTAX INTEGER {
    none(1),
    enrolled(2)
  }
  ACCESS read-write
  STATUS mandatory
  DESCRIPTION
    "Variable name: VPN_CONNECTION.LOCAL_CERT_REF
    WebUi Label: Local X.509 certificate
    This object is effective if and only if the 'mGuardVPNLocalCertNewRef'
    object contains the OID of this object. When this object is read, it
    always returns the value 'none'. When the value 'none' is written to
    this object, no local machine certificate is used."
  ::= { mGuardVPNConnectionEntry 56 }

-- VPN_CONNECTION.LOCAL_CERT_REF reference
mGuardVPNLocalCertNewRef OBJECT-TYPE
  SYNTAX OBJECT IDENTIFIER
  ACCESS read-write
  STATUS mandatory
  DESCRIPTION
    "Variable name: VPN_CONNECTION.LOCAL_CERT_REF
    WebUi Label: Local X.509 certificate
    When this object contains the OID of an 'mGuardCertsLocalIndex'
    object, the corresponding X.509 certificate and private key is used
    for this side of the VPN connection. To select a local machine
    certificate in this manner, write the OID of the corresponding
    'mGuardCertsLocalIndex' object to this object. To disable this
    feature, set the 'mGuardVPNLocalCertNewValue' object."
  ::= { mGuardVPNConnectionEntry 57 }

-- VPN_CONNECTION.CONTROL_INV
mGuardVPNconControlInv OBJECT-TYPE
  SYNTAX INTEGER {
    yes(1),
    no(2)
  }
  ACCESS read-write
  STATUS mandatory
  DESCRIPTION
    "Variable name: VPN_CONNECTION.CONTROL_INV
    WebUi Label: Use inverted control logic
    Configures whether the activation input is low active."
  ::= { mGuardVPNConnectionEntry 70 }

-- VPN_CONNECTION.DPD_TIMEOUT
mGuardVPNDPDTimeout OBJECT-TYPE
  SYNTAX INTEGER
  ACCESS read-write
  STATUS mandatory
  DESCRIPTION
    "Variable name: VPN_CONNECTION.DPD_TIMEOUT
    WebUi Label: Timeout for absent sign of life after which peer is assumed dead
    Interval in seconds before declaring the remote end as dead after
    sending the first DPD request. The default value is 120."
  ::= { mGuardVPNConnectionEntry 41 }

-- VPN_CONNECTION.TIMEOUT_SECONDS
mGuardVPNTimeoutSeconds OBJECT-TYPE
  SYNTAX INTEGER(0..2592000)
  ACCESS read-write
  STATUS mandatory
  DESCRIPTION
    "Variable name: VPN_CONNECTION.TIMEOUT_SECONDS
    WebUi Label: Deactivation timeout
    Specifies the timeout after that a VPN connection will be stopped when
    not traffic is going through the tunnel."
  ::= { mGuardVPNConnectionEntry 80 }

-- VPN_CONNECTION.REMOTE_CERT_REF
mGuardVPNRemoteCACertValue OBJECT-TYPE
  SYNTAX INTEGER {
    selfsigned(1),
    anyca(2)
  }
  ACCESS read-write
  STATUS mandatory
  DESCRIPTION
    "Variable name: VPN_CONNECTION.REMOTE_CERT_REF
    WebUi Label: Remote CA certificate
    This object is effective if and only if the 'mGuardVPNRemoteCACertRef'
    object contains the OID of this object. Options: 'anyca' to accept the
    remote peer's certificate in case it is signed by at least one CA in
    mGuardCertsCA. 'selfsigned' to require the peer to use the same
    certificate as stored in mGuardVPNx509."
  ::= { mGuardVPNConnectionEntry 58 }

-- VPN_CONNECTION.REMOTE_CERT_REF reference
mGuardVPNRemoteCACertRef OBJECT-TYPE
  SYNTAX OBJECT IDENTIFIER
  ACCESS read-write
  STATUS mandatory
  DESCRIPTION
    "Variable name: VPN_CONNECTION.REMOTE_CERT_REF
    WebUi Label: Remote CA certificate
    When this object contains the OID of an 'mGuardCertsCAIndex' object,
    the corresponding CA certificate is used to validate the remote VPN
    peer. To select a CA certificate in this manner, write the OID of the
    corresponding 'mGuardCertsCAIndex' object to this object. To disable
    this feature, set the 'mGuardVPNRemoteCACertValue' object."
  ::= { mGuardVPNConnectionEntry 59 }

-- VPN_CONNECTION.VPN_AUTH
mGuardVPNauthType OBJECT-TYPE
  SYNTAX INTEGER {
    psk(1),
    x509(2)
  }
  ACCESS read-write
  STATUS mandatory
  DESCRIPTION
    "Variable name: VPN_CONNECTION.VPN_AUTH
    WebUi Label: Authentication method
    Authentication mode of the VPN connection: psk / x509"
  ::= { mGuardVPNConnectionEntry 10 }

-- VPN_CONNECTION.INITIATE
mGuardVPNconStartUp OBJECT-TYPE
  SYNTAX INTEGER {
    initiate(1),
    waitForRemote(2),
    initiateOnDemand(3)
  }
  ACCESS read-write
  STATUS mandatory
  DESCRIPTION
    "Variable name: VPN_CONNECTION.INITIATE
    WebUi Label: Connection startup
    Recognize the startup of the VPN connection or wait for connection
    startup of the remote gateway."
  ::= { mGuardVPNConnectionEntry 19 }

-- VPN_CONNECTION.MODECFG_DNS1
mGuardVPNconModeCfgDNS1 OBJECT-TYPE
  SYNTAX IpAddress
  ACCESS read-write
  STATUS mandatory
  DESCRIPTION
    "Variable name: VPN_CONNECTION.MODECFG_DNS1
    WebUi Label: 1st DNS server for the peer
    MODECFG server mode: The address of the first DNS server announced to
    the client."
  ::= { mGuardVPNConnectionEntry 73 }

-- VPN_CONNECTION.FW_INCOMING
mGuardVPNFWINuuid OBJECT-TYPE
  SYNTAX DisplayString
  ACCESS read-only
  STATUS mandatory
  DESCRIPTION
    "Variable name: VPN_CONNECTION.FW_INCOMING
    WebUi Label: --
    Universally Unique Identifier (UUID, RFC 4122) used for
    mGuardVPNFWINTable logging."
  ::= { mGuardVPNConnectionEntry 81 }


-- VPN_CONNECTION.FW_INCOMING table
mGuardVPNFWINTable OBJECT-TYPE
  SYNTAX SEQUENCE OF MGuardVPNFWINEntry
  ACCESS not-accessible
  STATUS mandatory
  DESCRIPTION
    "A table of VPN_CONNECTION.FW_INCOMING"
  ::= { mGuardVPNFW 1 }

-- VPN_CONNECTION.FW_INCOMING table entry
mGuardVPNFWINEntry OBJECT-TYPE
  SYNTAX MGuardVPNFWINEntry
  ACCESS not-accessible
  STATUS mandatory
  DESCRIPTION
    "An entry of VPN_CONNECTION.FW_INCOMING"
  INDEX { mGuardVPNconIndex, mGuardVPNFWINruleIndex }
  ::= { mGuardVPNFWINTable 1 }

MGuardVPNFWINEntry ::= SEQUENCE {
  mGuardVPNFWINruleIndex                   INTEGER,
  mGuardVPNFWINproto                       INTEGER,
  mGuardVPNFWINlog                         INTEGER,
  mGuardVPNFWINRowStatus                   RowStatus,
  mGuardVPNFWINcomment                     DisplayString,
  mGuardVPNFWINtargetRef                   OBJECT IDENTIFIER,
  mGuardVPNFWINtargetValue                 INTEGER,
  mGuardVPNFWINsourceIPOrGroupValue        DisplayString,
  mGuardVPNFWINsourceIPOrGroupRef          OBJECT IDENTIFIER,
  mGuardVPNFWINdestinationIPOrGroupValue   DisplayString,
  mGuardVPNFWINdestinationIPOrGroupRef     OBJECT IDENTIFIER,
  mGuardVPNFWINsportOrGroupValue           DisplayString,
  mGuardVPNFWINsportOrGroupRef             OBJECT IDENTIFIER,
  mGuardVPNFWINdportOrGroupValue           DisplayString,
  mGuardVPNFWINdportOrGroupRef             OBJECT IDENTIFIER
}

-- VPN_CONNECTION.FW_INCOMING table index
mGuardVPNFWINruleIndex OBJECT-TYPE
  SYNTAX INTEGER (1..2147483647)
  ACCESS not-accessible
  STATUS mandatory
  DESCRIPTION
    "Index to VPN_CONNECTION.FW_INCOMING"
  ::= { mGuardVPNFWINEntry 2 }

-- VPN_CONNECTION.FW_INCOMING row status
mGuardVPNFWINRowStatus OBJECT-TYPE
  SYNTAX RowStatus
  ACCESS read-write
  STATUS mandatory
  DESCRIPTION
    "RowStatus of VPN_CONNECTION.FW_INCOMING"
  ::= { mGuardVPNFWINEntry 10 }

-- VPN_CONNECTION.FW_INCOMING.COMMENT
mGuardVPNFWINcomment OBJECT-TYPE
  SYNTAX DisplayString
  ACCESS read-write
  STATUS mandatory
  DESCRIPTION
    "Variable name: VPN_CONNECTION.FW_INCOMING.COMMENT
    WebUi Label: Comment
    Commentary or name for this rule."
  ::= { mGuardVPNFWINEntry 11 }

-- VPN_CONNECTION.FW_INCOMING.FROM_PORT
mGuardVPNFWINsportOrGroupValue OBJECT-TYPE
  SYNTAX DisplayString
  ACCESS read-write
  STATUS mandatory
  DESCRIPTION
    "Variable name: VPN_CONNECTION.FW_INCOMING.FROM_PORT
    WebUi Label: From port
    The rule's source port"
  ::= { mGuardVPNFWINEntry 20 }

-- VPN_CONNECTION.FW_INCOMING.FROM_PORT reference
mGuardVPNFWINsportOrGroupRef OBJECT-TYPE
  SYNTAX OBJECT IDENTIFIER
  ACCESS read-write
  STATUS mandatory
  DESCRIPTION
    "Variable name: VPN_CONNECTION.FW_INCOMING.FROM_PORT
    WebUi Label: From port
    The rule's source port as reference to port group"
  ::= { mGuardVPNFWINEntry 21 }

-- VPN_CONNECTION.FW_INCOMING.LOG
mGuardVPNFWINlog OBJECT-TYPE
  SYNTAX INTEGER {
    yes(1),
    no(2)
  }
  ACCESS read-write
  STATUS mandatory
  DESCRIPTION
    "Variable name: VPN_CONNECTION.FW_INCOMING.LOG
    WebUi Label: Log
    Log packets matching this rule."
  ::= { mGuardVPNFWINEntry 9 }

-- VPN_CONNECTION.FW_INCOMING.PROTO
mGuardVPNFWINproto OBJECT-TYPE
  SYNTAX INTEGER {
    tcp(1),
    udp(2),
    icmp(3),
    all(4),
    gre(5)
  }
  ACCESS read-write
  STATUS mandatory
  DESCRIPTION
    "Variable name: VPN_CONNECTION.FW_INCOMING.PROTO
    WebUi Label: Protocol
    The rule's transport protocol"
  ::= { mGuardVPNFWINEntry 8 }

-- VPN_CONNECTION.FW_INCOMING.FROM_IP
mGuardVPNFWINsourceIPOrGroupValue OBJECT-TYPE
  SYNTAX DisplayString
  ACCESS read-write
  STATUS mandatory
  DESCRIPTION
    "Variable name: VPN_CONNECTION.FW_INCOMING.FROM_IP
    WebUi Label: From IP
    The rule's source IP address"
  ::= { mGuardVPNFWINEntry 16 }

-- VPN_CONNECTION.FW_INCOMING.FROM_IP reference
mGuardVPNFWINsourceIPOrGroupRef OBJECT-TYPE
  SYNTAX OBJECT IDENTIFIER
  ACCESS read-write
  STATUS mandatory
  DESCRIPTION
    "Variable name: VPN_CONNECTION.FW_INCOMING.FROM_IP
    WebUi Label: From IP
    The rule's source IP address as reference to IP group"
  ::= { mGuardVPNFWINEntry 17 }

-- VPN_CONNECTION.FW_INCOMING.IN_IP
mGuardVPNFWINdestinationIPOrGroupValue OBJECT-TYPE
  SYNTAX DisplayString
  ACCESS read-write
  STATUS mandatory
  DESCRIPTION
    "Variable name: VPN_CONNECTION.FW_INCOMING.IN_IP
    WebUi Label: To IP
    The rule's destination IP address"
  ::= { mGuardVPNFWINEntry 18 }

-- VPN_CONNECTION.FW_INCOMING.IN_IP reference
mGuardVPNFWINdestinationIPOrGroupRef OBJECT-TYPE
  SYNTAX OBJECT IDENTIFIER
  ACCESS read-write
  STATUS mandatory
  DESCRIPTION
    "Variable name: VPN_CONNECTION.FW_INCOMING.IN_IP
    WebUi Label: To IP
    The rule's destination IP address as reference to IP group"
  ::= { mGuardVPNFWINEntry 19 }

-- VPN_CONNECTION.FW_INCOMING.TARGET_REF
mGuardVPNFWINtargetValue OBJECT-TYPE
  SYNTAX INTEGER {
    accept(1),
    reject(2),
    drop(3)
  }
  ACCESS read-write
  STATUS mandatory
  DESCRIPTION
    "Variable name: VPN_CONNECTION.FW_INCOMING.TARGET_REF
    WebUi Label: Action
    The rule's target. This object is effective if and only if the
    'mGuardVPNFWINtargetRef' object contains the OID of this object."
  ::= { mGuardVPNFWINEntry 13 }

-- VPN_CONNECTION.FW_INCOMING.TARGET_REF reference
mGuardVPNFWINtargetRef OBJECT-TYPE
  SYNTAX OBJECT IDENTIFIER
  ACCESS read-write
  STATUS mandatory
  DESCRIPTION
    "Variable name: VPN_CONNECTION.FW_INCOMING.TARGET_REF
    WebUi Label: Action
    Set this object to the OID of an 'mGuardFWRuleIndex' to select a
    firewall ruleset as this rule's target. Set this object to the OID of
    the 'mGuardVPNFWINtargetValue' object to choose a target from that
    objects range."
  ::= { mGuardVPNFWINEntry 12 }

-- VPN_CONNECTION.FW_INCOMING.IN_PORT
mGuardVPNFWINdportOrGroupValue OBJECT-TYPE
  SYNTAX DisplayString
  ACCESS read-write
  STATUS mandatory
  DESCRIPTION
    "Variable name: VPN_CONNECTION.FW_INCOMING.IN_PORT
    WebUi Label: To port
    The rule's destination port"
  ::= { mGuardVPNFWINEntry 22 }

-- VPN_CONNECTION.FW_INCOMING.IN_PORT reference
mGuardVPNFWINdportOrGroupRef OBJECT-TYPE
  SYNTAX OBJECT IDENTIFIER
  ACCESS read-write
  STATUS mandatory
  DESCRIPTION
    "Variable name: VPN_CONNECTION.FW_INCOMING.IN_PORT
    WebUi Label: To port
    The rule's destination port as reference to port group"
  ::= { mGuardVPNFWINEntry 23 }

-- VPN_CONNECTION.INTERFACE
mGuardVPNInterface OBJECT-TYPE
  SYNTAX INTEGER {
    intern(1),
    extern(2),
    extern2(3),
    dialin(4),
    byIp(5),
    dmz0(6)
  }
  ACCESS read-write
  STATUS mandatory
  DESCRIPTION
    "Variable name: VPN_CONNECTION.INTERFACE
    WebUi Label: Interface to use for gateway setting %any
    Specify the interface if mGuardVPNremGW is set to %any. The mGuard
    will listen on this device for incoming VPN connections. If the value
    is byIp then the device is implicitly specified by mGuardVPNHostIp"
  ::= { mGuardVPNConnectionEntry 60 }

-- VPN_CONNECTION.VPN_NAME
mGuardVPNconName OBJECT-TYPE
  SYNTAX DisplayString
  ACCESS read-write
  STATUS mandatory
  DESCRIPTION
    "Variable name: VPN_CONNECTION.VPN_NAME
    WebUi Label: A descriptive name for the connection
    Descriptive name of the connection."
  ::= { mGuardVPNConnectionEntry 2 }

-- VPN_CONNECTION.REKEYFUZZ
mGuardVPNRekeyFuzz OBJECT-TYPE
  SYNTAX INTEGER
  ACCESS read-write
  STATUS mandatory
  DESCRIPTION
    "Variable name: VPN_CONNECTION.REKEYFUZZ
    WebUi Label: Re-key fuzz (applies to all re-key margins)
    Rekey fuzz (in percent)."
  ::= { mGuardVPNConnectionEntry 36 }

-- VPN_CONNECTION.LOG_DEFAULT_INCOMING
mGuardVPNFWLogDefIn OBJECT-TYPE
  SYNTAX INTEGER {
    yes(1),
    no(2)
  }
  ACCESS read-write
  STATUS mandatory
  DESCRIPTION
    "Variable name: VPN_CONNECTION.LOG_DEFAULT_INCOMING
    WebUi Label: Log entries for unknown connection attempts
    Log entries for undefined incoming connection attempts?"
  ::= { mGuardVPNConnectionEntry 22 }

-- VPN_DEBUG_CONTROL
mGuardVPNIkeLog OBJECT-TYPE
  SYNTAX INTEGER {
    yes(1),
    no(2)
  }
  ACCESS read-write
  STATUS mandatory
  DESCRIPTION
    "Variable name: VPN_DEBUG_CONTROL
    WebUi Label: Log verbose information on IKE
    Log verbose information on IKE ?"
  ::= { mGuardVPNSettings 6 }

-- VPN_DYNIP_HOSTNAME
mGuardVPNDynDNSRegHostname OBJECT-TYPE
  SYNTAX DisplayString
  ACCESS read-write
  STATUS mandatory
  DESCRIPTION
    "Variable name: VPN_DYNIP_HOSTNAME
    WebUi Label: DynDNS hostname
    Hostname to register"
  ::= { mGuardVPNDynDNSRegister 7 }

-- VPN_DYNIP_LOGIN
mGuardVPNDynDNSRegLogin OBJECT-TYPE
  SYNTAX DisplayString
  ACCESS read-write
  STATUS mandatory
  DESCRIPTION
    "Variable name: VPN_DYNIP_LOGIN
    WebUi Label: DynDNS login
    Login for DynDNS server."
  ::= { mGuardVPNDynDNSRegister 4 }

-- VPN_DYNIP_PASSWD
mGuardVPNDynDNSRegPasswd OBJECT-TYPE
  SYNTAX DisplayString
  ACCESS read-write
  STATUS mandatory
  DESCRIPTION
    "Variable name: VPN_DYNIP_PASSWD
    WebUi Label: DynDNS password
    Password for DynDNS server."
  ::= { mGuardVPNDynDNSRegister 5 }

-- VPN_DYNIP_PORT
mGuardVPNDynDNSRegPort OBJECT-TYPE
  SYNTAX INTEGER(1..65535)
  ACCESS read-write
  STATUS mandatory
  DESCRIPTION
    "Variable name: VPN_DYNIP_PORT
    WebUi Label: DynDNS port
    Port number of the DynDNS server."
  ::= { mGuardVPNDynDNSRegister 10 }

-- VPN_DYNIP_PROVIDER
mGuardVPNDynDNSRegProviderNew OBJECT-TYPE
  SYNTAX INTEGER {
    dyndns-compatible(1),
    dyndns(2),
    no-ip(3),
    freedns(4),
    easydns(5),
    dnsexit(6),
    dynu(7)
  }
  ACCESS read-write
  STATUS mandatory
  DESCRIPTION
    "Variable name: VPN_DYNIP_PROVIDER
    WebUi Label: DynDNS provider
    DynDNS provider"
  ::= { mGuardVPNDynDNSRegister 9 }

-- VPN_DYNIP_REGISTER
mGuardVPNDynDNSReg OBJECT-TYPE
  SYNTAX INTEGER {
    yes(1),
    no(2)
  }
  ACCESS read-write
  STATUS mandatory
  DESCRIPTION
    "Variable name: VPN_DYNIP_REGISTER
    WebUi Label: Register the mGuard at a DynDNS service
    Register the mGuard at a DynDNS service: no, yes"
  ::= { mGuardVPNDynDNSRegister 1 }

-- VPN_DYNIP_REGISTER_INTERVAL
mGuardVPNDynDNSRegInterval OBJECT-TYPE
  SYNTAX INTEGER
  ACCESS read-write
  STATUS mandatory
  DESCRIPTION
    "Variable name: VPN_DYNIP_REGISTER_INTERVAL
    WebUi Label: Refresh interval
    Refresh interval for registration."
  ::= { mGuardVPNDynDNSRegister 2 }

-- VPN_DYNIP_SERVER
mGuardVPNDynDNSRegServer OBJECT-TYPE
  SYNTAX DisplayString
  ACCESS read-write
  STATUS mandatory
  DESCRIPTION
    "Variable name: VPN_DYNIP_SERVER
    WebUi Label: DynDNS server
    DynDNS server."
  ::= { mGuardVPNDynDNSRegister 3 }

-- VPN_DYNIP_WATCH
mGuardVPNDynDNSCheckDo OBJECT-TYPE
  SYNTAX INTEGER {
    yes(1),
    no(2)
  }
  ACCESS read-write
  STATUS mandatory
  DESCRIPTION
    "Variable name: VPN_DYNIP_WATCH
    WebUi Label: Watch hostnames of remote VPN gateways
    Should hostnames of remote VPN gateways be checked after certain time
    intervals in case they are at a DynDNS provider? : no,yes"
  ::= { mGuardVPNDynDNSCheck 1 }

-- VPN_DYNIP_WATCH_INTERVAL
mGuardVPNDynDNSCheckRefresh OBJECT-TYPE
  SYNTAX INTEGER
  ACCESS read-write
  STATUS mandatory
  DESCRIPTION
    "Variable name: VPN_DYNIP_WATCH_INTERVAL
    WebUi Label: Refresh interval
    Refresh interval for checking DNS names of remote VPN peers."
  ::= { mGuardVPNDynDNSCheck 2 }

-- VPN_ESP_AESC_SBOX
mGuardVPNAESCBox OBJECT-TYPE
  SYNTAX DisplayString
  ACCESS read-write
  STATUS mandatory
  DESCRIPTION
    "Variable name: VPN_ESP_AESC_SBOX
    WebUi Label: Modified S-Box for AESC algorithm
    The S-box to be used for the AESC algorithm. The original Rijndael box
    will be used if empty."
  ::= { mGuardVPNSettings 38 }

-- VPN_HIDE_TOS
mGuardVPNHideTos OBJECT-TYPE
  SYNTAX INTEGER {
    yes(1),
    no(2)
  }
  ACCESS read-write
  STATUS mandatory
  DESCRIPTION
    "Variable name: VPN_HIDE_TOS
    WebUi Label: Hide Type of Service (TOS) Bit
    When set to yes the TOS bit will be cleared on IPsec output."
  ::= { mGuardVPNSettings 7 }

-- VPN_HUB_AND_SPOKE
mGuardVPNHubAndSpoke OBJECT-TYPE
  SYNTAX INTEGER {
    yes(1),
    no(2)
  }
  ACCESS read-write
  STATUS mandatory
  DESCRIPTION
    "Variable name: VPN_HUB_AND_SPOKE
    WebUi Label: Allow packet forwarding between VPN connections
    Route traffic between IPsec VPN connections."
  ::= { mGuardVPNSettings 11 }

-- VPN_IKE_FRAGMENTATION
mGuardVPNIkeFragmentation OBJECT-TYPE
  SYNTAX INTEGER {
    yes(1),
    no(2)
  }
  ACCESS read-write
  STATUS mandatory
  DESCRIPTION
    "Variable name: VPN_IKE_FRAGMENTATION
    WebUi Label: IKE fragmentation
    Fragment IKE Packets to traverse broken NAT Routers."
  ::= { mGuardVPNSettings 36 }

-- VPN_IPSEC0_MTU
mGuardVPNmtu OBJECT-TYPE
  SYNTAX INTEGER
  ACCESS read-write
  STATUS mandatory
  DESCRIPTION
    "Variable name: VPN_IPSEC0_MTU
    WebUi Label: IPsec MTU (default is 16260)
    ipsec0 mtu"
  ::= { mGuardVPNSettings 8 }

-- VPN_IPTUN_ENABLE
mGuardVPNIPtunEnable OBJECT-TYPE
  SYNTAX INTEGER {
    yes(1),
    no(2)
  }
  ACCESS read-write
  STATUS mandatory
  DESCRIPTION
    "Variable name: VPN_IPTUN_ENABLE
    WebUi Label: Listen for incoming VPN connections, which are encapsulated
    Allow incoming VPN connections to use legacy TCP tunneling"
  ::= { mGuardVPNSettings 17 }

-- VPN_IPTUN_LISTEN_PORT
mGuardVPNIPtunListenport OBJECT-TYPE
  SYNTAX DisplayString
  ACCESS read-write
  STATUS mandatory
  DESCRIPTION
    "Variable name: VPN_IPTUN_LISTEN_PORT
    WebUi Label: TCP port to listen on
    TCP port for incoming VPN connections that use legacy TCP tunneling"
  ::= { mGuardVPNSettings 18 }

-- VPN_IPTUN_POOL
mGuardVPNIPtunPool OBJECT-TYPE
  SYNTAX INTEGER(0..63)
  ACCESS read-write
  STATUS mandatory
  DESCRIPTION
    "Variable name: VPN_IPTUN_POOL
    WebUi Label: Server ID (0-63)
    TCP tunneling server ID."
  ::= { mGuardVPNSettings 19 }

-- VPN_KEEP_ALIVE_FORCE
mGuardVPNNatTKeepAliveForce OBJECT-TYPE
  SYNTAX INTEGER {
    yes(1),
    no(2)
  }
  ACCESS read-write
  STATUS mandatory
  DESCRIPTION
    "Variable name: VPN_KEEP_ALIVE_FORCE
    WebUi Label: Force NAT-T keepalive
    Force NAT-T Keepalive ?"
  ::= { mGuardVPNSettings 5 }

-- VPN_KEEP_ALIVE_INTERVAL
mGuardVPNNatTKeepAliveInterval OBJECT-TYPE
  SYNTAX INTEGER
  ACCESS read-write
  STATUS mandatory
  DESCRIPTION
    "Variable name: VPN_KEEP_ALIVE_INTERVAL
    WebUi Label: NAT-T keepalive interval (in seconds, default is 300)
    NAT-T Keepalive Interval (in seconds). Keepalives will tell the NAT
    router not to close the connection."
  ::= { mGuardVPNSettings 4 }

-- VPN_LOG_PERSIST_ENABLED
mGuardVPNLogPersistEnable OBJECT-TYPE
  SYNTAX INTEGER {
    no(2),
    yes(3)
  }
  ACCESS read-write
  STATUS mandatory
  DESCRIPTION
    "Variable name: VPN_LOG_PERSIST_ENABLED
    WebUi Label: Archive diagnostic messages for VPN connections
    Enable persistent logging globally (yes) or for nph-vpn/CMD button
    usecase. Global activation may not be supported on some platforms or
    releases."
  ::= { mGuardVPNLogPersist 1 }

-- VPN_LOG_PERSIST_FAILURES_ONLY
mGuardVPNLogPersistFailuresOnly OBJECT-TYPE
  SYNTAX INTEGER {
    yes(1),
    no(2)
  }
  ACCESS read-write
  STATUS mandatory
  DESCRIPTION
    "Variable name: VPN_LOG_PERSIST_FAILURES_ONLY
    WebUi Label: Archive diagnostic messages only upon failure
    Enable persistent logging for failures."
  ::= { mGuardVPNLogPersist 2 }

-- VPN_LOG_PERSIST_LEAST_FREE
mGuardVPNLogPersistLeastFree OBJECT-TYPE
  SYNTAX INTEGER(1536..4096)
  ACCESS read-write
  STATUS mandatory
  DESCRIPTION
    "Variable name: VPN_LOG_PERSIST_LEAST_FREE
    WebUi Label: --
    Minimum amount of free persistent memory in kByte to be left."
  ::= { mGuardVPNLogPersist 3 }

-- VPN_LOG_PERSIST_MAX_FPS
mGuardVPNLogPersistMaxFPS OBJECT-TYPE
  SYNTAX INTEGER(0..4)
  ACCESS read-write
  STATUS mandatory
  DESCRIPTION
    "Variable name: VPN_LOG_PERSIST_MAX_FPS
    WebUi Label: --
    Maximum number of logs per second to be archived."
  ::= { mGuardVPNLogPersist 5 }

-- VPN_MSS
mGuardVPNIPsecTcpMss OBJECT-TYPE
  SYNTAX INTEGER
  ACCESS read-write
  STATUS mandatory
  DESCRIPTION
    "Variable name: VPN_MSS
    WebUi Label: When not 0, clamp TCP's maximum segment size to this value inside all
     IPsec connections.
    When not 0, clamp TCP's Maximum Segment Size to this value inside all
    IPsec connections."
  ::= { mGuardVPNSettings 13 }

-- VPN_NAT_TRAVERSAL
mGuardVPNNatTraversal OBJECT-TYPE
  SYNTAX INTEGER {
    on(1),
    off(2)
  }
  ACCESS read-write
  STATUS mandatory
  DESCRIPTION
    "Variable name: VPN_NAT_TRAVERSAL
    WebUi Label: NAT traversal
    Encapsulate ESP traffic into IKE (UDP) packets to pass IPsec unaware
    NAT routers."
  ::= { mGuardVPNSettings 2 }

-- VPN_NO_CR_SEND
mGuardVPNNoCertReqSend OBJECT-TYPE
  SYNTAX INTEGER {
    yes(1),
    no(2)
  }
  ACCESS read-write
  STATUS mandatory
  DESCRIPTION
    "Variable name: VPN_NO_CR_SEND
    WebUi Label: Never send certificate requests
    Don't send certificate requests?"
  ::= { mGuardVPNSettings 10 }

-- VPN_PORTFLOATING
mGuardVPNNatTPortfloating OBJECT-TYPE
  SYNTAX INTEGER {
    on(1),
    off(2)
  }
  ACCESS read-write
  STATUS mandatory
  DESCRIPTION
    "Variable name: VPN_PORTFLOATING
    WebUi Label: Enable NAT-T portfloating
    Some NAT routers fail to perform NAT originating low UDP ports. This
    option moves IKE from UDP 500 to UDP 4500 if possible"
  ::= { mGuardVPNSettings 3 }

-- VPN_ROUTING
mGuardVPNRoutingType OBJECT-TYPE
  SYNTAX INTEGER {
    all-interfaces(1),
    intern-only(2)
  }
  ACCESS read-write
  STATUS mandatory
  DESCRIPTION
    "Variable name: VPN_ROUTING
    WebUi Label: --
    Interfaces allowed to communicate via VPN: all interfaces (strongly
    discouraged, unsupported) or internal interface only."
  ::= { mGuardVPNSettings 16 }

-- VPN_TCPENCAP_ENABLE
mGuardVPNTCPEncapEnable OBJECT-TYPE
  SYNTAX INTEGER {
    yes(1),
    no(2)
  }
  ACCESS read-write
  STATUS mandatory
  DESCRIPTION
    "Variable name: VPN_TCPENCAP_ENABLE
    WebUi Label: Enable Path Finder for mGuard Secure VPN Client
    Allow incoming VPN connections to use NCP compatible TCP tunneling"
  ::= { mGuardVPNSettings 34 }

-- VPN_TCPENCAP_LISTEN_PORT
mGuardVPNTCPEncapListenport OBJECT-TYPE
  SYNTAX DisplayString
  ACCESS read-write
  STATUS mandatory
  DESCRIPTION
    "Variable name: VPN_TCPENCAP_LISTEN_PORT
    WebUi Label: TCP port to listen on
    TCP port for incoming VPN connections that use NCP compatible TCP
    tunneling"
  ::= { mGuardVPNSettings 35 }

-- VPN_UNIQUE_IDS
mGuardVPNRequireUniqueIDs OBJECT-TYPE
  SYNTAX INTEGER {
    yes(1),
    no(2)
  }
  ACCESS read-write
  STATUS mandatory
  DESCRIPTION
    "Variable name: VPN_UNIQUE_IDS
    WebUi Label: Require unique IDs
    Allow only one open connection per identity (i.e. X.509 certificate)."
  ::= { mGuardVPNSettings 1 }

-- WWW_LANGUAGE
mGuardWebInterfaceLanguage OBJECT-TYPE
  SYNTAX INTEGER {
    automatic(1),
    english(2),
    german(3),
    japanese(4)
  }
  ACCESS read-write
  STATUS mandatory
  DESCRIPTION
    "Variable name: WWW_LANGUAGE
    WebUi Label: Language
    The language used in the web interface."
  ::= { mGuardWebInterface 1 }

-- WWW_LEVEL
mGuardWebInterfaceExpertLevel OBJECT-TYPE
  SYNTAX INTEGER {
    normal(10),
    experienced(50),
    expert(90)
  }
  ACCESS read-write
  STATUS mandatory
  DESCRIPTION
    "Variable name: WWW_LEVEL
    WebUi Label: Level of Detail
    The detail level for hiding or showing option. Note: options showing
    in levels higher than normal are not documented in the user manual and
    should only be used in special cases as side effects may occur. Not
    all setups with these additional options are guaranteed to work."
  ::= { mGuardWebInterface 4 }

-- WWW_PASSWORD
mGuardAdminPassword OBJECT-TYPE
  SYNTAX DisplayString
  ACCESS read-write
  STATUS mandatory
  DESCRIPTION
    "Variable name: WWW_PASSWORD
    WebUi Label: Administrator password
    Changes the password for the user admin who can modify the system
    configuration, install software updates and initiate a system reboot."
  ::= { mGuardPasswords 2 }

-- WWW_TIMEOUT
mGuardWebInterfaceSessionTimeout OBJECT-TYPE
  SYNTAX INTEGER(15..86400)
  ACCESS read-write
  STATUS mandatory
  DESCRIPTION
    "Variable name: WWW_TIMEOUT
    WebUi Label: Session timeout
    The session timeout of the web interface in seconds. If no changes are
    submitted for the specified time, the session is terminated and it
    will be necessary to log in again before further use of the web
    interface."
  ::= { mGuardWebInterface 2 }

-- cifsim/validaterep action
mGuardActionCIFSValidateRep OBJECT IDENTIFIER ::= { mGuardActions 1 1 }

-- cifsim/validaterep action status
mGuardActionCIFSValidateRepStatus OBJECT-TYPE
  SYNTAX MGuardActionStatus
  ACCESS read-write
  STATUS mandatory
  DESCRIPTION
    "Validate the signature of the last report. Since the report is
    stored externally, it could possibly be modified. It requires either
    the 'rowid' of the CIFS_FILE_CHECK or the 'name' of the scanned share
    as parameter.

    This object is used is used to prepare or submit the
    mGuardActionCIFSValidateRep action, and to obtain its status."
  ::= { mGuardActionCIFSValidateRep 1 }

-- cifsim/validaterep action result
mGuardActionCIFSValidateRepResult OBJECT-TYPE
  SYNTAX DisplayString
  ACCESS read-only
  STATUS mandatory
  DESCRIPTION
    "After running the mGuardActionCIFSValidateRep action, the result
    can be read from this object."
  ::= { mGuardActionCIFSValidateRep 2 }

-- cifsim/validaterep action name parameter
mGuardActionCIFSValidateRepNameParam OBJECT-TYPE
  SYNTAX DisplayString
  ACCESS read-write
  STATUS mandatory
  DESCRIPTION
    "The 'name' parameter to the mGuardActionCIFSValidateRep action."
  ::= { mGuardActionCIFSValidateRep 3 }

-- cifsim/check-start action
mGuardActionCIFSCheckStart OBJECT IDENTIFIER ::= { mGuardActions 1 2 }

-- cifsim/check-start action status
mGuardActionCIFSCheckStartStatus OBJECT-TYPE
  SYNTAX MGuardActionStatus
  ACCESS read-write
  STATUS mandatory
  DESCRIPTION
    "Start a CIFS Integrity Monitoring check for the given 'rowid' of
    the CIFS_FILE_CHECK or the 'name' of the scanned share as parameter.

    This object is used is used to prepare or submit the
    mGuardActionCIFSCheckStart action, and to obtain its status."
  ::= { mGuardActionCIFSCheckStart 1 }

-- cifsim/check-start action result
mGuardActionCIFSCheckStartResult OBJECT-TYPE
  SYNTAX DisplayString
  ACCESS read-only
  STATUS mandatory
  DESCRIPTION
    "After running the mGuardActionCIFSCheckStart action, the result
    can be read from this object."
  ::= { mGuardActionCIFSCheckStart 2 }

-- cifsim/check-start action name parameter
mGuardActionCIFSCheckStartNameParam OBJECT-TYPE
  SYNTAX DisplayString
  ACCESS read-write
  STATUS mandatory
  DESCRIPTION
    "The 'name' parameter to the mGuardActionCIFSCheckStart action."
  ::= { mGuardActionCIFSCheckStart 3 }

-- cifsim/init-start action
mGuardActionCIFSInitStart OBJECT IDENTIFIER ::= { mGuardActions 1 3 }

-- cifsim/init-start action status
mGuardActionCIFSInitStartStatus OBJECT-TYPE
  SYNTAX MGuardActionStatus
  ACCESS read-write
  STATUS mandatory
  DESCRIPTION
    "Initialize a CIFS Integrity Monitoring database for the given 'rowid' of
    the CIFS_FILE_CHECK or the 'name' of the scanned share as parameter.

    This object is used is used to prepare or submit the
    mGuardActionCIFSInitStart action, and to obtain its status."
  ::= { mGuardActionCIFSInitStart 1 }

-- cifsim/init-start action result
mGuardActionCIFSInitStartResult OBJECT-TYPE
  SYNTAX DisplayString
  ACCESS read-only
  STATUS mandatory
  DESCRIPTION
    "After running the mGuardActionCIFSInitStart action, the result
    can be read from this object."
  ::= { mGuardActionCIFSInitStart 2 }

-- cifsim/init-start action name parameter
mGuardActionCIFSInitStartNameParam OBJECT-TYPE
  SYNTAX DisplayString
  ACCESS read-write
  STATUS mandatory
  DESCRIPTION
    "The 'name' parameter to the mGuardActionCIFSInitStart action."
  ::= { mGuardActionCIFSInitStart 3 }

-- cifsim/access-scan action
mGuardActionCIFSAccessScan OBJECT IDENTIFIER ::= { mGuardActions 1 4 }

-- cifsim/access-scan action status
mGuardActionCIFSAccessScanStatus OBJECT-TYPE
  SYNTAX MGuardActionStatus
  ACCESS read-write
  STATUS mandatory
  DESCRIPTION
    "Start a CIFS Integrity Monitoring file access scan for the given 'rowid' of
    the CIFS_FILE_CHECK or the 'name' of the scanned share as parameter.

    This object is used is used to prepare or submit the
    mGuardActionCIFSAccessScan action, and to obtain its status."
  ::= { mGuardActionCIFSAccessScan 1 }

-- cifsim/access-scan action result
mGuardActionCIFSAccessScanResult OBJECT-TYPE
  SYNTAX DisplayString
  ACCESS read-only
  STATUS mandatory
  DESCRIPTION
    "After running the mGuardActionCIFSAccessScan action, the result
    can be read from this object."
  ::= { mGuardActionCIFSAccessScan 2 }

-- cifsim/access-scan action name parameter
mGuardActionCIFSAccessScanNameParam OBJECT-TYPE
  SYNTAX DisplayString
  ACCESS read-write
  STATUS mandatory
  DESCRIPTION
    "The 'name' parameter to the mGuardActionCIFSAccessScan action."
  ::= { mGuardActionCIFSAccessScan 3 }

-- cifsim/cancel action
mGuardActionCIFSCancel OBJECT IDENTIFIER ::= { mGuardActions 1 5 }

-- cifsim/cancel action status
mGuardActionCIFSCancelStatus OBJECT-TYPE
  SYNTAX MGuardActionStatus
  ACCESS read-write
  STATUS mandatory
  DESCRIPTION
    "Interrupt a currently running CIFS Integrity Monitoring check for
    the given 'rowid' of the CIFS_FILE_CHECK or the 'name' of
    the scanned share as parameter.

    This object is used is used to prepare or submit the
    mGuardActionCIFSCancel action, and to obtain its status."
  ::= { mGuardActionCIFSCancel 1 }

-- cifsim/cancel action result
mGuardActionCIFSCancelResult OBJECT-TYPE
  SYNTAX DisplayString
  ACCESS read-only
  STATUS mandatory
  DESCRIPTION
    "After running the mGuardActionCIFSCancel action, the result
    can be read from this object."
  ::= { mGuardActionCIFSCancel 2 }

-- cifsim/cancel action name parameter
mGuardActionCIFSCancelNameParam OBJECT-TYPE
  SYNTAX DisplayString
  ACCESS read-write
  STATUS mandatory
  DESCRIPTION
    "The 'name' parameter to the mGuardActionCIFSCancel action."
  ::= { mGuardActionCIFSCancel 3 }

-- cifsim/erase-db action
mGuardActionCIFSEraseDB OBJECT IDENTIFIER ::= { mGuardActions 1 6 }

-- cifsim/erase-db action status
mGuardActionCIFSEraseDBStatus OBJECT-TYPE
  SYNTAX MGuardActionStatus
  ACCESS read-write
  STATUS mandatory
  DESCRIPTION
    "Delete a CIFS Integrity Monitoring database for the given 'rowid' of
    the CIFS_FILE_CHECK or the 'name' of the scanned share as parameter.

    This object is used is used to prepare or submit the
    mGuardActionCIFSEraseDB action, and to obtain its status."
  ::= { mGuardActionCIFSEraseDB 1 }

-- cifsim/erase-db action result
mGuardActionCIFSEraseDBResult OBJECT-TYPE
  SYNTAX DisplayString
  ACCESS read-only
  STATUS mandatory
  DESCRIPTION
    "After running the mGuardActionCIFSEraseDB action, the result
    can be read from this object."
  ::= { mGuardActionCIFSEraseDB 2 }

-- cifsim/erase-db action name parameter
mGuardActionCIFSEraseDBNameParam OBJECT-TYPE
  SYNTAX DisplayString
  ACCESS read-write
  STATUS mandatory
  DESCRIPTION
    "The 'name' parameter to the mGuardActionCIFSEraseDB action."
  ::= { mGuardActionCIFSEraseDB 3 }

-- vpn/start action
mGuardActionVPNStart OBJECT IDENTIFIER ::= { mGuardActions 2 1 }

-- vpn/start action status
mGuardActionVPNStartStatus OBJECT-TYPE
  SYNTAX MGuardActionStatus
  ACCESS read-write
  STATUS mandatory
  DESCRIPTION
    "Start the VPN connection described by the 'rowid' or the 'name'
    of the connection. This action will not wait until the connection
    is established, but return immediately after initiation.

    This object is used is used to prepare or submit the
    mGuardActionVPNStart action, and to obtain its status."
  ::= { mGuardActionVPNStart 1 }

-- vpn/start action result
mGuardActionVPNStartResult OBJECT-TYPE
  SYNTAX DisplayString
  ACCESS read-only
  STATUS mandatory
  DESCRIPTION
    "After running the mGuardActionVPNStart action, the result
    can be read from this object."
  ::= { mGuardActionVPNStart 2 }

-- vpn/start action name parameter
mGuardActionVPNStartNameParam OBJECT-TYPE
  SYNTAX DisplayString
  ACCESS read-write
  STATUS mandatory
  DESCRIPTION
    "The 'name' parameter to the mGuardActionVPNStart action."
  ::= { mGuardActionVPNStart 3 }

-- vpn/stop action
mGuardActionVPNStop OBJECT IDENTIFIER ::= { mGuardActions 2 2 }

-- vpn/stop action status
mGuardActionVPNStopStatus OBJECT-TYPE
  SYNTAX MGuardActionStatus
  ACCESS read-write
  STATUS mandatory
  DESCRIPTION
    "Stop the VPN connection described by the 'rowid' or the 'name'
    of the connection. This action will not wait until the connection
    is teared down completely, but return immediately after
    triggering the stop.

    This object is used is used to prepare or submit the
    mGuardActionVPNStop action, and to obtain its status."
  ::= { mGuardActionVPNStop 1 }

-- vpn/stop action result
mGuardActionVPNStopResult OBJECT-TYPE
  SYNTAX DisplayString
  ACCESS read-only
  STATUS mandatory
  DESCRIPTION
    "After running the mGuardActionVPNStop action, the result
    can be read from this object."
  ::= { mGuardActionVPNStop 2 }

-- vpn/stop action name parameter
mGuardActionVPNStopNameParam OBJECT-TYPE
  SYNTAX DisplayString
  ACCESS read-write
  STATUS mandatory
  DESCRIPTION
    "The 'name' parameter to the mGuardActionVPNStop action."
  ::= { mGuardActionVPNStop 3 }

-- vpn/restart action
mGuardActionVPNRestart OBJECT IDENTIFIER ::= { mGuardActions 2 3 }

-- vpn/restart action status
mGuardActionVPNRestartStatus OBJECT-TYPE
  SYNTAX MGuardActionStatus
  ACCESS read-write
  STATUS mandatory
  DESCRIPTION
    "Restart the VPN connection described by the 'rowid' or the 'name'
    of the connection. This action will not wait until the connection
    is restarted completely, but return immediately after
    triggering the restart.

    This object is used is used to prepare or submit the
    mGuardActionVPNRestart action, and to obtain its status."
  ::= { mGuardActionVPNRestart 1 }

-- vpn/restart action result
mGuardActionVPNRestartResult OBJECT-TYPE
  SYNTAX DisplayString
  ACCESS read-only
  STATUS mandatory
  DESCRIPTION
    "After running the mGuardActionVPNRestart action, the result
    can be read from this object."
  ::= { mGuardActionVPNRestart 2 }

-- vpn/restart action name parameter
mGuardActionVPNRestartNameParam OBJECT-TYPE
  SYNTAX DisplayString
  ACCESS read-write
  STATUS mandatory
  DESCRIPTION
    "The 'name' parameter to the mGuardActionVPNRestart action."
  ::= { mGuardActionVPNRestart 3 }

-- openvpn/start action
mGuardActionOpenVPNStart OBJECT IDENTIFIER ::= { mGuardActions 3 1 }

-- openvpn/start action status
mGuardActionOpenVPNStartStatus OBJECT-TYPE
  SYNTAX MGuardActionStatus
  ACCESS read-write
  STATUS mandatory
  DESCRIPTION
    "Start the OpenVPN connection described by the 'rowid' or the 'name'
    of the connection. This action will not wait until the connection
    is established, but return immediately after initiation.

    This object is used is used to prepare or submit the
    mGuardActionOpenVPNStart action, and to obtain its status."
  ::= { mGuardActionOpenVPNStart 1 }

-- openvpn/start action result
mGuardActionOpenVPNStartResult OBJECT-TYPE
  SYNTAX DisplayString
  ACCESS read-only
  STATUS mandatory
  DESCRIPTION
    "After running the mGuardActionOpenVPNStart action, the result
    can be read from this object."
  ::= { mGuardActionOpenVPNStart 2 }

-- openvpn/start action name parameter
mGuardActionOpenVPNStartNameParam OBJECT-TYPE
  SYNTAX DisplayString
  ACCESS read-write
  STATUS mandatory
  DESCRIPTION
    "The 'name' parameter to the mGuardActionOpenVPNStart action."
  ::= { mGuardActionOpenVPNStart 3 }

-- openvpn/stop action
mGuardActionOpenVPNStop OBJECT IDENTIFIER ::= { mGuardActions 3 2 }

-- openvpn/stop action status
mGuardActionOpenVPNStopStatus OBJECT-TYPE
  SYNTAX MGuardActionStatus
  ACCESS read-write
  STATUS mandatory
  DESCRIPTION
    "Stop the OpenVPN connection described by the 'rowid' or the 'name'
    of the connection. This action will not wait until the connection
    is teared down completely, but return immediately after
    triggering the stop.

    This object is used is used to prepare or submit the
    mGuardActionOpenVPNStop action, and to obtain its status."
  ::= { mGuardActionOpenVPNStop 1 }

-- openvpn/stop action result
mGuardActionOpenVPNStopResult OBJECT-TYPE
  SYNTAX DisplayString
  ACCESS read-only
  STATUS mandatory
  DESCRIPTION
    "After running the mGuardActionOpenVPNStop action, the result
    can be read from this object."
  ::= { mGuardActionOpenVPNStop 2 }

-- openvpn/stop action name parameter
mGuardActionOpenVPNStopNameParam OBJECT-TYPE
  SYNTAX DisplayString
  ACCESS read-write
  STATUS mandatory
  DESCRIPTION
    "The 'name' parameter to the mGuardActionOpenVPNStop action."
  ::= { mGuardActionOpenVPNStop 3 }

-- switch/purge-arlt action
mGuardActionSwitchPurgeARLT OBJECT IDENTIFIER ::= { mGuardActions 4 1 }

-- switch/purge-arlt action status
mGuardActionSwitchPurgeARLTStatus OBJECT-TYPE
  SYNTAX MGuardActionStatus
  ACCESS read-write
  STATUS mandatory
  DESCRIPTION
    "Delete all learned MAC addresses from the
    Address-Resolution-Lookup-Table of the builtin Switch

    This object is used is used to prepare or submit the
    mGuardActionSwitchPurgeARLT action, and to obtain its status."
  ::= { mGuardActionSwitchPurgeARLT 1 }

-- switch/purge-arlt action result
mGuardActionSwitchPurgeARLTResult OBJECT-TYPE
  SYNTAX DisplayString
  ACCESS read-only
  STATUS mandatory
  DESCRIPTION
    "After running the mGuardActionSwitchPurgeARLT action, the result
    can be read from this object."
  ::= { mGuardActionSwitchPurgeARLT 2 }

-- switch/reset-phy-counters action
mGuardActionSwitchResetPhyCounters OBJECT IDENTIFIER ::= { mGuardActions 4 2 }

-- switch/reset-phy-counters action status
mGuardActionSwitchResetPhyCountersStatus OBJECT-TYPE
  SYNTAX MGuardActionStatus
  ACCESS read-write
  STATUS mandatory
  DESCRIPTION
    "Reset the PHY counters of the builtin Switch

    This object is used is used to prepare or submit the
    mGuardActionSwitchResetPhyCounters action, and to obtain its status."
  ::= { mGuardActionSwitchResetPhyCounters 1 }

-- switch/reset-phy-counters action result
mGuardActionSwitchResetPhyCountersResult OBJECT-TYPE
  SYNTAX DisplayString
  ACCESS read-only
  STATUS mandatory
  DESCRIPTION
    "After running the mGuardActionSwitchResetPhyCounters action, the result
    can be read from this object."
  ::= { mGuardActionSwitchResetPhyCounters 2 }

-- ecs/save action
mGuardActionECSSave OBJECT IDENTIFIER ::= { mGuardActions 5 1 }

-- ecs/save action status
mGuardActionECSSaveStatus OBJECT-TYPE
  SYNTAX MGuardActionStatus
  ACCESS read-write
  STATUS mandatory
  DESCRIPTION
    "Save the currently active configuration on the
    External-Configuration-Storage (ECS). The 'rootpw' must match the
    root password of the device, where the ECS will be loaded.

    This object is used is used to prepare or submit the
    mGuardActionECSSave action, and to obtain its status."
  ::= { mGuardActionECSSave 1 }

-- ecs/save action result
mGuardActionECSSaveResult OBJECT-TYPE
  SYNTAX DisplayString
  ACCESS read-only
  STATUS mandatory
  DESCRIPTION
    "After running the mGuardActionECSSave action, the result
    can be read from this object."
  ::= { mGuardActionECSSave 2 }

-- ecs/save action rootpw parameter
mGuardActionECSSaveRootpwParam OBJECT-TYPE
  SYNTAX DisplayString
  ACCESS read-write
  STATUS mandatory
  DESCRIPTION
    "The 'rootpw' parameter to the mGuardActionECSSave action."
  ::= { mGuardActionECSSave 3 }

-- ecs/load action
mGuardActionECSLoad OBJECT IDENTIFIER ::= { mGuardActions 5 2 }

-- ecs/load action status
mGuardActionECSLoadStatus OBJECT-TYPE
  SYNTAX MGuardActionStatus
  ACCESS read-write
  STATUS mandatory
  DESCRIPTION
    "Load the configuration from an External-Configuration-Storage (ECS).

    This object is used is used to prepare or submit the
    mGuardActionECSLoad action, and to obtain its status."
  ::= { mGuardActionECSLoad 1 }

-- ecs/load action result
mGuardActionECSLoadResult OBJECT-TYPE
  SYNTAX DisplayString
  ACCESS read-only
  STATUS mandatory
  DESCRIPTION
    "After running the mGuardActionECSLoad action, the result
    can be read from this object."
  ::= { mGuardActionECSLoad 2 }

-- gsm/sms action
mGuardActionGSMSMS OBJECT IDENTIFIER ::= { mGuardActions 6 2 }

-- gsm/sms action status
mGuardActionGSMSMSStatus OBJECT-TYPE
  SYNTAX MGuardActionStatus
  ACCESS read-write
  STATUS mandatory
  DESCRIPTION
    "Send a text message 'msg' the mobile number provided in 'dial'.

    This object is used is used to prepare or submit the
    mGuardActionGSMSMS action, and to obtain its status."
  ::= { mGuardActionGSMSMS 1 }

-- gsm/sms action result
mGuardActionGSMSMSResult OBJECT-TYPE
  SYNTAX DisplayString
  ACCESS read-only
  STATUS mandatory
  DESCRIPTION
    "After running the mGuardActionGSMSMS action, the result
    can be read from this object."
  ::= { mGuardActionGSMSMS 2 }

-- gsm/sms action dial parameter
mGuardActionGSMSMSDialParam OBJECT-TYPE
  SYNTAX DisplayString
  ACCESS read-write
  STATUS mandatory
  DESCRIPTION
    "The 'dial' parameter to the mGuardActionGSMSMS action."
  ::= { mGuardActionGSMSMS 3 }

-- gsm/sms action msg parameter
mGuardActionGSMSMSMsgParam OBJECT-TYPE
  SYNTAX DisplayString
  ACCESS read-write
  STATUS mandatory
  DESCRIPTION
    "The 'msg' parameter to the mGuardActionGSMSMS action."
  ::= { mGuardActionGSMSMS 4 }

-- cdma/otasp_verizon action
mGuardActionCDMAOTASPVerizon OBJECT IDENTIFIER ::= { mGuardActions 7 1 }

-- cdma/otasp_verizon action status
mGuardActionCDMAOTASPVerizonStatus OBJECT-TYPE
  SYNTAX MGuardActionStatus
  ACCESS read-write
  STATUS mandatory
  DESCRIPTION
    "Initialize the Verizon registration procedure

    This object is used is used to prepare or submit the
    mGuardActionCDMAOTASPVerizon action, and to obtain its status."
  ::= { mGuardActionCDMAOTASPVerizon 1 }

-- cdma/otasp_verizon action result
mGuardActionCDMAOTASPVerizonResult OBJECT-TYPE
  SYNTAX DisplayString
  ACCESS read-only
  STATUS mandatory
  DESCRIPTION
    "After running the mGuardActionCDMAOTASPVerizon action, the result
    can be read from this object."
  ::= { mGuardActionCDMAOTASPVerizon 2 }

-- userfw/login action
mGuardActionUserFWLogin OBJECT IDENTIFIER ::= { mGuardActions 8 1 }

-- userfw/login action status
mGuardActionUserFWLoginStatus OBJECT-TYPE
  SYNTAX MGuardActionStatus
  ACCESS read-write
  STATUS mandatory
  DESCRIPTION
    "Login the user 'name' as User Firewall user with group 'group'
    from IP 'ip', authorized by 'method'.

    This object is used is used to prepare or submit the
    mGuardActionUserFWLogin action, and to obtain its status."
  ::= { mGuardActionUserFWLogin 1 }

-- userfw/login action result
mGuardActionUserFWLoginResult OBJECT-TYPE
  SYNTAX DisplayString
  ACCESS read-only
  STATUS mandatory
  DESCRIPTION
    "After running the mGuardActionUserFWLogin action, the result
    can be read from this object."
  ::= { mGuardActionUserFWLogin 2 }

-- userfw/login action name parameter
mGuardActionUserFWLoginNameParam OBJECT-TYPE
  SYNTAX DisplayString
  ACCESS read-write
  STATUS mandatory
  DESCRIPTION
    "The 'name' parameter to the mGuardActionUserFWLogin action."
  ::= { mGuardActionUserFWLogin 3 }

-- userfw/login action group parameter
mGuardActionUserFWLoginGroupParam OBJECT-TYPE
  SYNTAX DisplayString
  ACCESS read-write
  STATUS mandatory
  DESCRIPTION
    "The 'group' parameter to the mGuardActionUserFWLogin action."
  ::= { mGuardActionUserFWLogin 4 }

-- userfw/login action ip parameter
mGuardActionUserFWLoginIpParam OBJECT-TYPE
  SYNTAX IpAddress
  ACCESS read-write
  STATUS mandatory
  DESCRIPTION
    "The 'ip' parameter to the mGuardActionUserFWLogin action."
  ::= { mGuardActionUserFWLogin 5 }

-- userfw/login action method parameter
mGuardActionUserFWLoginMethodParam OBJECT-TYPE
  SYNTAX DisplayString
  ACCESS read-write
  STATUS mandatory
  DESCRIPTION
    "The 'method' parameter to the mGuardActionUserFWLogin action."
  ::= { mGuardActionUserFWLogin 6 }

-- userfw/logout action
mGuardActionUserFWLogout OBJECT IDENTIFIER ::= { mGuardActions 8 2 }

-- userfw/logout action status
mGuardActionUserFWLogoutStatus OBJECT-TYPE
  SYNTAX MGuardActionStatus
  ACCESS read-write
  STATUS mandatory
  DESCRIPTION
    "Logout the User Firewall user 'name' with IP 'ip'.

    This object is used is used to prepare or submit the
    mGuardActionUserFWLogout action, and to obtain its status."
  ::= { mGuardActionUserFWLogout 1 }

-- userfw/logout action result
mGuardActionUserFWLogoutResult OBJECT-TYPE
  SYNTAX DisplayString
  ACCESS read-only
  STATUS mandatory
  DESCRIPTION
    "After running the mGuardActionUserFWLogout action, the result
    can be read from this object."
  ::= { mGuardActionUserFWLogout 2 }

-- userfw/logout action name parameter
mGuardActionUserFWLogoutNameParam OBJECT-TYPE
  SYNTAX DisplayString
  ACCESS read-write
  STATUS mandatory
  DESCRIPTION
    "The 'name' parameter to the mGuardActionUserFWLogout action."
  ::= { mGuardActionUserFWLogout 3 }

-- userfw/logout action ip parameter
mGuardActionUserFWLogoutIpParam OBJECT-TYPE
  SYNTAX IpAddress
  ACCESS read-write
  STATUS mandatory
  DESCRIPTION
    "The 'ip' parameter to the mGuardActionUserFWLogout action."
  ::= { mGuardActionUserFWLogout 4 }

-- fwrules/active action
mGuardActionFWRulesActive OBJECT IDENTIFIER ::= { mGuardActions 9 1 }

-- fwrules/active action status
mGuardActionFWRulesActiveStatus OBJECT-TYPE
  SYNTAX MGuardActionStatus
  ACCESS read-write
  STATUS mandatory
  DESCRIPTION
    "Activate the Firewall rule set with Row id 'rowid' or the rule set
    name 'name'.

    This object is used is used to prepare or submit the
    mGuardActionFWRulesActive action, and to obtain its status."
  ::= { mGuardActionFWRulesActive 1 }

-- fwrules/active action result
mGuardActionFWRulesActiveResult OBJECT-TYPE
  SYNTAX DisplayString
  ACCESS read-only
  STATUS mandatory
  DESCRIPTION
    "After running the mGuardActionFWRulesActive action, the result
    can be read from this object."
  ::= { mGuardActionFWRulesActive 2 }

-- fwrules/active action name parameter
mGuardActionFWRulesActiveNameParam OBJECT-TYPE
  SYNTAX DisplayString
  ACCESS read-write
  STATUS mandatory
  DESCRIPTION
    "The 'name' parameter to the mGuardActionFWRulesActive action."
  ::= { mGuardActionFWRulesActive 3 }

-- fwrules/inactive action
mGuardActionFWRulesInactive OBJECT IDENTIFIER ::= { mGuardActions 9 2 }

-- fwrules/inactive action status
mGuardActionFWRulesInactiveStatus OBJECT-TYPE
  SYNTAX MGuardActionStatus
  ACCESS read-write
  STATUS mandatory
  DESCRIPTION
    "Deactivate the Firewall rule set with Row id 'rowid' or the rule set
    name 'name'

    This object is used is used to prepare or submit the
    mGuardActionFWRulesInactive action, and to obtain its status."
  ::= { mGuardActionFWRulesInactive 1 }

-- fwrules/inactive action result
mGuardActionFWRulesInactiveResult OBJECT-TYPE
  SYNTAX DisplayString
  ACCESS read-only
  STATUS mandatory
  DESCRIPTION
    "After running the mGuardActionFWRulesInactive action, the result
    can be read from this object."
  ::= { mGuardActionFWRulesInactive 2 }

-- fwrules/inactive action name parameter
mGuardActionFWRulesInactiveNameParam OBJECT-TYPE
  SYNTAX DisplayString
  ACCESS read-write
  STATUS mandatory
  DESCRIPTION
    "The 'name' parameter to the mGuardActionFWRulesInactive action."
  ::= { mGuardActionFWRulesInactive 3 }

-- tools/ping action
mGuardActionToolsPing OBJECT IDENTIFIER ::= { mGuardActions 10 1 }

-- tools/ping action status
mGuardActionToolsPingStatus OBJECT-TYPE
  SYNTAX MGuardActionStatus
  ACCESS read-write
  STATUS mandatory
  DESCRIPTION
    "Start 5 pings to the destination in 'target'

    This object is used is used to prepare or submit the
    mGuardActionToolsPing action, and to obtain its status."
  ::= { mGuardActionToolsPing 1 }

-- tools/ping action result
mGuardActionToolsPingResult OBJECT-TYPE
  SYNTAX DisplayString
  ACCESS read-only
  STATUS mandatory
  DESCRIPTION
    "After running the mGuardActionToolsPing action, the result
    can be read from this object."
  ::= { mGuardActionToolsPing 2 }

-- tools/ping action target parameter
mGuardActionToolsPingTargetParam OBJECT-TYPE
  SYNTAX DisplayString
  ACCESS read-write
  STATUS mandatory
  DESCRIPTION
    "The 'target' parameter to the mGuardActionToolsPing action."
  ::= { mGuardActionToolsPing 3 }

-- tools/traceroute action
mGuardActionToolsTraceroute OBJECT IDENTIFIER ::= { mGuardActions 10 2 }

-- tools/traceroute action status
mGuardActionToolsTracerouteStatus OBJECT-TYPE
  SYNTAX MGuardActionStatus
  ACCESS read-write
  STATUS mandatory
  DESCRIPTION
    "Start a traceroute to the destination IP or hostname

    This object is used is used to prepare or submit the
    mGuardActionToolsTraceroute action, and to obtain its status."
  ::= { mGuardActionToolsTraceroute 1 }

-- tools/traceroute action result
mGuardActionToolsTracerouteResult OBJECT-TYPE
  SYNTAX DisplayString
  ACCESS read-only
  STATUS mandatory
  DESCRIPTION
    "After running the mGuardActionToolsTraceroute action, the result
    can be read from this object."
  ::= { mGuardActionToolsTraceroute 2 }

-- tools/traceroute action target parameter
mGuardActionToolsTracerouteTargetParam OBJECT-TYPE
  SYNTAX DisplayString
  ACCESS read-write
  STATUS mandatory
  DESCRIPTION
    "The 'target' parameter to the mGuardActionToolsTraceroute action."
  ::= { mGuardActionToolsTraceroute 3 }

-- tools/traceroute action nslookup parameter
mGuardActionToolsTracerouteNslookupParam OBJECT-TYPE
  SYNTAX INTEGER {
    yes(1),
    no(2)
  }
  ACCESS read-write
  STATUS mandatory
  DESCRIPTION
    "The 'nslookup' parameter to the mGuardActionToolsTraceroute action."
  ::= { mGuardActionToolsTraceroute 4 }

-- tools/dnslookup action
mGuardActionToolsDNSLookup OBJECT IDENTIFIER ::= { mGuardActions 10 3 }

-- tools/dnslookup action status
mGuardActionToolsDNSLookupStatus OBJECT-TYPE
  SYNTAX MGuardActionStatus
  ACCESS read-write
  STATUS mandatory
  DESCRIPTION
    "Lookup the given DNS hostname and return the corresponding IP.
    Checks whether a DNS hostname resolves to an IP.

    This object is used is used to prepare or submit the
    mGuardActionToolsDNSLookup action, and to obtain its status."
  ::= { mGuardActionToolsDNSLookup 1 }

-- tools/dnslookup action result
mGuardActionToolsDNSLookupResult OBJECT-TYPE
  SYNTAX DisplayString
  ACCESS read-only
  STATUS mandatory
  DESCRIPTION
    "After running the mGuardActionToolsDNSLookup action, the result
    can be read from this object."
  ::= { mGuardActionToolsDNSLookup 2 }

-- tools/dnslookup action target parameter
mGuardActionToolsDNSLookupTargetParam OBJECT-TYPE
  SYNTAX DisplayString
  ACCESS read-write
  STATUS mandatory
  DESCRIPTION
    "The 'target' parameter to the mGuardActionToolsDNSLookup action."
  ::= { mGuardActionToolsDNSLookup 3 }

-- tools/ikeping action
mGuardActionToolsIKEPing OBJECT IDENTIFIER ::= { mGuardActions 10 4 }

-- tools/ikeping action status
mGuardActionToolsIKEPingStatus OBJECT-TYPE
  SYNTAX MGuardActionStatus
  ACCESS read-write
  STATUS mandatory
  DESCRIPTION
    "Tries to reach the given gateway on UDP Port 500.

    This object is used is used to prepare or submit the
    mGuardActionToolsIKEPing action, and to obtain its status."
  ::= { mGuardActionToolsIKEPing 1 }

-- tools/ikeping action result
mGuardActionToolsIKEPingResult OBJECT-TYPE
  SYNTAX DisplayString
  ACCESS read-only
  STATUS mandatory
  DESCRIPTION
    "After running the mGuardActionToolsIKEPing action, the result
    can be read from this object."
  ::= { mGuardActionToolsIKEPing 2 }

-- tools/ikeping action target parameter
mGuardActionToolsIKEPingTargetParam OBJECT-TYPE
  SYNTAX DisplayString
  ACCESS read-write
  STATUS mandatory
  DESCRIPTION
    "The 'target' parameter to the mGuardActionToolsIKEPing action."
  ::= { mGuardActionToolsIKEPing 3 }

-- system/reboot action
mGuardActionSystemReboot OBJECT IDENTIFIER ::= { mGuardActions 11 1 }

-- system/reboot action status
mGuardActionSystemRebootStatus OBJECT-TYPE
  SYNTAX MGuardActionStatus
  ACCESS read-write
  STATUS mandatory
  DESCRIPTION
    "Reboots the device.

    This object is used is used to prepare or submit the
    mGuardActionSystemReboot action, and to obtain its status."
  ::= { mGuardActionSystemReboot 1 }

-- system/reboot action result
mGuardActionSystemRebootResult OBJECT-TYPE
  SYNTAX DisplayString
  ACCESS read-only
  STATUS mandatory
  DESCRIPTION
    "After running the mGuardActionSystemReboot action, the result
    can be read from this object."
  ::= { mGuardActionSystemReboot 2 }

-- system/testpull action
mGuardActionSystemTestpull OBJECT IDENTIFIER ::= { mGuardActions 11 2 }

-- system/testpull action status
mGuardActionSystemTestpullStatus OBJECT-TYPE
  SYNTAX MGuardActionStatus
  ACCESS read-write
  STATUS mandatory
  DESCRIPTION
    "Tries to download a configuration from the configured pull config
    server.

    This object is used is used to prepare or submit the
    mGuardActionSystemTestpull action, and to obtain its status."
  ::= { mGuardActionSystemTestpull 1 }

-- system/testpull action result
mGuardActionSystemTestpullResult OBJECT-TYPE
  SYNTAX DisplayString
  ACCESS read-only
  STATUS mandatory
  DESCRIPTION
    "After running the mGuardActionSystemTestpull action, the result
    can be read from this object."
  ::= { mGuardActionSystemTestpull 2 }

-- system/userlogin action
mGuardActionSystemUserLogin OBJECT IDENTIFIER ::= { mGuardActions 11 3 }

-- system/userlogin action status
mGuardActionSystemUserLoginStatus OBJECT-TYPE
  SYNTAX MGuardActionStatus
  ACCESS read-write
  STATUS mandatory
  DESCRIPTION
    "Perform the user login for enabling the firewall and VPN for the authorized user.

    This object is used is used to prepare or submit the
    mGuardActionSystemUserLogin action, and to obtain its status."
  ::= { mGuardActionSystemUserLogin 1 }

-- system/userlogin action result
mGuardActionSystemUserLoginResult OBJECT-TYPE
  SYNTAX DisplayString
  ACCESS read-only
  STATUS mandatory
  DESCRIPTION
    "After running the mGuardActionSystemUserLogin action, the result
    can be read from this object."
  ::= { mGuardActionSystemUserLogin 2 }

-- system/userlogout action
mGuardActionSystemUserLogout OBJECT IDENTIFIER ::= { mGuardActions 11 4 }

-- system/userlogout action status
mGuardActionSystemUserLogoutStatus OBJECT-TYPE
  SYNTAX MGuardActionStatus
  ACCESS read-write
  STATUS mandatory
  DESCRIPTION
    "Perform the user logout for the authorized user.

    This object is used is used to prepare or submit the
    mGuardActionSystemUserLogout action, and to obtain its status."
  ::= { mGuardActionSystemUserLogout 1 }

-- system/userlogout action result
mGuardActionSystemUserLogoutResult OBJECT-TYPE
  SYNTAX DisplayString
  ACCESS read-only
  STATUS mandatory
  DESCRIPTION
    "After running the mGuardActionSystemUserLogout action, the result
    can be read from this object."
  ::= { mGuardActionSystemUserLogout 2 }

-- system/key-renewal action
mGuardActionSystemKeyRenewal OBJECT IDENTIFIER ::= { mGuardActions 11 5 }

-- system/key-renewal action status
mGuardActionSystemKeyRenewalStatus OBJECT-TYPE
  SYNTAX MGuardActionStatus
  ACCESS read-write
  STATUS mandatory
  DESCRIPTION
    "Generates new RSA keys for HTTPS and SSH login.

    This object is used is used to prepare or submit the
    mGuardActionSystemKeyRenewal action, and to obtain its status."
  ::= { mGuardActionSystemKeyRenewal 1 }

-- system/key-renewal action result
mGuardActionSystemKeyRenewalResult OBJECT-TYPE
  SYNTAX DisplayString
  ACCESS read-only
  STATUS mandatory
  DESCRIPTION
    "After running the mGuardActionSystemKeyRenewal action, the result
    can be read from this object."
  ::= { mGuardActionSystemKeyRenewal 2 }

-- system/localtime action
mGuardActionSystemLocaltime OBJECT IDENTIFIER ::= { mGuardActions 11 7 }

-- system/localtime action status
mGuardActionSystemLocaltimeStatus OBJECT-TYPE
  SYNTAX MGuardActionStatus
  ACCESS read-write
  STATUS mandatory
  DESCRIPTION
    "Set the current local time and RTC time respecting the
    configured Timezone. Replacing the RTC_TIME configuration variable.

    This object is used is used to prepare or submit the
    mGuardActionSystemLocaltime action, and to obtain its status."
  ::= { mGuardActionSystemLocaltime 1 }

-- system/localtime action result
mGuardActionSystemLocaltimeResult OBJECT-TYPE
  SYNTAX DisplayString
  ACCESS read-only
  STATUS mandatory
  DESCRIPTION
    "After running the mGuardActionSystemLocaltime action, the result
    can be read from this object."
  ::= { mGuardActionSystemLocaltime 2 }

-- system/localtime action localtime parameter
mGuardActionSystemLocaltimeLocaltimeParam OBJECT-TYPE
  SYNTAX DisplayString
  ACCESS read-write
  STATUS mandatory
  DESCRIPTION
    "The 'localtime' parameter to the mGuardActionSystemLocaltime action."
  ::= { mGuardActionSystemLocaltime 3 }

-- license/request action
mGuardActionLicenseRequest OBJECT IDENTIFIER ::= { mGuardActions 12 1 }

-- license/request action status
mGuardActionLicenseRequestStatus OBJECT-TYPE
  SYNTAX MGuardActionStatus
  ACCESS read-write
  STATUS mandatory
  DESCRIPTION
    "Perform an online license request. Internet connection and DNS
    must be configured properly to succeed.

    This object is used is used to prepare or submit the
    mGuardActionLicenseRequest action, and to obtain its status."
  ::= { mGuardActionLicenseRequest 1 }

-- license/request action result
mGuardActionLicenseRequestResult OBJECT-TYPE
  SYNTAX DisplayString
  ACCESS read-only
  STATUS mandatory
  DESCRIPTION
    "After running the mGuardActionLicenseRequest action, the result
    can be read from this object."
  ::= { mGuardActionLicenseRequest 2 }

-- license/request action licence_serial parameter
mGuardActionLicenseRequestLicenceSerialParam OBJECT-TYPE
  SYNTAX DisplayString
  ACCESS read-write
  STATUS mandatory
  DESCRIPTION
    "The 'licence_serial' parameter to the mGuardActionLicenseRequest action."
  ::= { mGuardActionLicenseRequest 3 }

-- license/request action licence_key parameter
mGuardActionLicenseRequestLicenceKeyParam OBJECT-TYPE
  SYNTAX DisplayString
  ACCESS read-write
  STATUS mandatory
  DESCRIPTION
    "The 'licence_key' parameter to the mGuardActionLicenseRequest action."
  ::= { mGuardActionLicenseRequest 4 }

-- license/refresh action
mGuardActionLicenseRefresh OBJECT IDENTIFIER ::= { mGuardActions 12 2 }

-- license/refresh action status
mGuardActionLicenseRefreshStatus OBJECT-TYPE
  SYNTAX MGuardActionStatus
  ACCESS read-write
  STATUS mandatory
  DESCRIPTION
    "Downloads all issued licenses for this device and installs them if they
    do not already exist.

    This object is used is used to prepare or submit the
    mGuardActionLicenseRefresh action, and to obtain its status."
  ::= { mGuardActionLicenseRefresh 1 }

-- license/refresh action result
mGuardActionLicenseRefreshResult OBJECT-TYPE
  SYNTAX DisplayString
  ACCESS read-only
  STATUS mandatory
  DESCRIPTION
    "After running the mGuardActionLicenseRefresh action, the result
    can be read from this object."
  ::= { mGuardActionLicenseRefresh 2 }

-- update/online action
mGuardActionUpdateOnline OBJECT IDENTIFIER ::= { mGuardActions 13 1 }

-- update/online action status
mGuardActionUpdateOnlineStatus OBJECT-TYPE
  SYNTAX MGuardActionStatus
  ACCESS read-write
  STATUS mandatory
  DESCRIPTION
    "Initiates an online update to the version mentioned in the 'update' parameter.

    This object is used is used to prepare or submit the
    mGuardActionUpdateOnline action, and to obtain its status."
  ::= { mGuardActionUpdateOnline 1 }

-- update/online action result
mGuardActionUpdateOnlineResult OBJECT-TYPE
  SYNTAX DisplayString
  ACCESS read-only
  STATUS mandatory
  DESCRIPTION
    "After running the mGuardActionUpdateOnline action, the result
    can be read from this object."
  ::= { mGuardActionUpdateOnline 2 }

-- update/online action update parameter
mGuardActionUpdateOnlineUpdateParam OBJECT-TYPE
  SYNTAX DisplayString
  ACCESS read-write
  STATUS mandatory
  DESCRIPTION
    "The 'update' parameter to the mGuardActionUpdateOnline action."
  ::= { mGuardActionUpdateOnline 3 }

-- update/patches action
mGuardActionUpdatePatches OBJECT IDENTIFIER ::= { mGuardActions 13 2 }

-- update/patches action status
mGuardActionUpdatePatchesStatus OBJECT-TYPE
  SYNTAX MGuardActionStatus
  ACCESS read-write
  STATUS mandatory
  DESCRIPTION
    "Initiates an online patch-update.

    This object is used is used to prepare or submit the
    mGuardActionUpdatePatches action, and to obtain its status."
  ::= { mGuardActionUpdatePatches 1 }

-- update/patches action result
mGuardActionUpdatePatchesResult OBJECT-TYPE
  SYNTAX DisplayString
  ACCESS read-only
  STATUS mandatory
  DESCRIPTION
    "After running the mGuardActionUpdatePatches action, the result
    can be read from this object."
  ::= { mGuardActionUpdatePatches 2 }

-- update/minor action
mGuardActionUpdateMinor OBJECT IDENTIFIER ::= { mGuardActions 13 3 }

-- update/minor action status
mGuardActionUpdateMinorStatus OBJECT-TYPE
  SYNTAX MGuardActionStatus
  ACCESS read-write
  STATUS mandatory
  DESCRIPTION
    "Initiates an online minor-update.

    This object is used is used to prepare or submit the
    mGuardActionUpdateMinor action, and to obtain its status."
  ::= { mGuardActionUpdateMinor 1 }

-- update/minor action result
mGuardActionUpdateMinorResult OBJECT-TYPE
  SYNTAX DisplayString
  ACCESS read-only
  STATUS mandatory
  DESCRIPTION
    "After running the mGuardActionUpdateMinor action, the result
    can be read from this object."
  ::= { mGuardActionUpdateMinor 2 }

-- update/major action
mGuardActionUpdateMajor OBJECT IDENTIFIER ::= { mGuardActions 13 4 }

-- update/major action status
mGuardActionUpdateMajorStatus OBJECT-TYPE
  SYNTAX MGuardActionStatus
  ACCESS read-write
  STATUS mandatory
  DESCRIPTION
    "Initiates an online major-update.

    This object is used is used to prepare or submit the
    mGuardActionUpdateMajor action, and to obtain its status."
  ::= { mGuardActionUpdateMajor 1 }

-- update/major action result
mGuardActionUpdateMajorResult OBJECT-TYPE
  SYNTAX DisplayString
  ACCESS read-only
  STATUS mandatory
  DESCRIPTION
    "After running the mGuardActionUpdateMajor action, the result
    can be read from this object."
  ::= { mGuardActionUpdateMajor 2 }

-- profile/save action
mGuardActionProfileSave OBJECT IDENTIFIER ::= { mGuardActions 14 1 }

-- profile/save action status
mGuardActionProfileSaveStatus OBJECT-TYPE
  SYNTAX MGuardActionStatus
  ACCESS read-write
  STATUS mandatory
  DESCRIPTION
    "This object is used is used to prepare or submit the
    mGuardActionProfileSave action, and to obtain its status."
  ::= { mGuardActionProfileSave 1 }

-- profile/save action result
mGuardActionProfileSaveResult OBJECT-TYPE
  SYNTAX DisplayString
  ACCESS read-only
  STATUS mandatory
  DESCRIPTION
    "After running the mGuardActionProfileSave action, the result
    can be read from this object."
  ::= { mGuardActionProfileSave 2 }

-- profile/save action name parameter
mGuardActionProfileSaveNameParam OBJECT-TYPE
  SYNTAX DisplayString
  ACCESS read-write
  STATUS mandatory
  DESCRIPTION
    "The 'name' parameter to the mGuardActionProfileSave action."
  ::= { mGuardActionProfileSave 3 }

-- profile/restore action
mGuardActionProfileRestore OBJECT IDENTIFIER ::= { mGuardActions 14 2 }

-- profile/restore action status
mGuardActionProfileRestoreStatus OBJECT-TYPE
  SYNTAX MGuardActionStatus
  ACCESS read-write
  STATUS mandatory
  DESCRIPTION
    "This object is used is used to prepare or submit the
    mGuardActionProfileRestore action, and to obtain its status."
  ::= { mGuardActionProfileRestore 1 }

-- profile/restore action result
mGuardActionProfileRestoreResult OBJECT-TYPE
  SYNTAX DisplayString
  ACCESS read-only
  STATUS mandatory
  DESCRIPTION
    "After running the mGuardActionProfileRestore action, the result
    can be read from this object."
  ::= { mGuardActionProfileRestore 2 }

-- profile/restore action name parameter
mGuardActionProfileRestoreNameParam OBJECT-TYPE
  SYNTAX DisplayString
  ACCESS read-write
  STATUS mandatory
  DESCRIPTION
    "The 'name' parameter to the mGuardActionProfileRestore action."
  ::= { mGuardActionProfileRestore 3 }

-- profile/delete action
mGuardActionProfileDelete OBJECT IDENTIFIER ::= { mGuardActions 14 3 }

-- profile/delete action status
mGuardActionProfileDeleteStatus OBJECT-TYPE
  SYNTAX MGuardActionStatus
  ACCESS read-write
  STATUS mandatory
  DESCRIPTION
    "This object is used is used to prepare or submit the
    mGuardActionProfileDelete action, and to obtain its status."
  ::= { mGuardActionProfileDelete 1 }

-- profile/delete action result
mGuardActionProfileDeleteResult OBJECT-TYPE
  SYNTAX DisplayString
  ACCESS read-only
  STATUS mandatory
  DESCRIPTION
    "After running the mGuardActionProfileDelete action, the result
    can be read from this object."
  ::= { mGuardActionProfileDelete 2 }

-- profile/delete action name parameter
mGuardActionProfileDeleteNameParam OBJECT-TYPE
  SYNTAX DisplayString
  ACCESS read-write
  STATUS mandatory
  DESCRIPTION
    "The 'name' parameter to the mGuardActionProfileDelete action."
  ::= { mGuardActionProfileDelete 3 }

-- ipsec/status action
mGuardActionIPsecStatus OBJECT IDENTIFIER ::= { mGuardActions 15 1 }

-- ipsec/status action status
mGuardActionIPsecStatusStatus OBJECT-TYPE
  SYNTAX MGuardActionStatus
  ACCESS read-write
  STATUS mandatory
  DESCRIPTION
    "nph-vpn.cgi?cmd=status

    This object is used is used to prepare or submit the
    mGuardActionIPsecStatus action, and to obtain its status."
  ::= { mGuardActionIPsecStatus 1 }

-- ipsec/status action result
mGuardActionIPsecStatusResult OBJECT-TYPE
  SYNTAX DisplayString
  ACCESS read-only
  STATUS mandatory
  DESCRIPTION
    "After running the mGuardActionIPsecStatus action, the result
    can be read from this object."
  ::= { mGuardActionIPsecStatus 2 }

-- ipsec/status action name parameter
mGuardActionIPsecStatusNameParam OBJECT-TYPE
  SYNTAX DisplayString
  ACCESS read-write
  STATUS mandatory
  DESCRIPTION
    "The 'name' parameter to the mGuardActionIPsecStatus action."
  ::= { mGuardActionIPsecStatus 3 }

-- ipsec/status action channel parameter
mGuardActionIPsecStatusChannelParam OBJECT-TYPE
  SYNTAX DisplayString
  ACCESS read-write
  STATUS mandatory
  DESCRIPTION
    "The 'channel' parameter to the mGuardActionIPsecStatus action."
  ::= { mGuardActionIPsecStatus 4 }

-- ipsec/clear action
mGuardActionIPsecClear OBJECT IDENTIFIER ::= { mGuardActions 15 2 }

-- ipsec/clear action status
mGuardActionIPsecClearStatus OBJECT-TYPE
  SYNTAX MGuardActionStatus
  ACCESS read-write
  STATUS mandatory
  DESCRIPTION
    "nph-vpn.cgi?cmd=clear
    
    The clear command is intended for central IPSec gateways
    without specific remote gateway ('%any')

    This object is used is used to prepare or submit the
    mGuardActionIPsecClear action, and to obtain its status."
  ::= { mGuardActionIPsecClear 1 }

-- ipsec/clear action result
mGuardActionIPsecClearResult OBJECT-TYPE
  SYNTAX DisplayString
  ACCESS read-only
  STATUS mandatory
  DESCRIPTION
    "After running the mGuardActionIPsecClear action, the result
    can be read from this object."
  ::= { mGuardActionIPsecClear 2 }

-- ipsec/clear action channel parameter
mGuardActionIPsecClearChannelParam OBJECT-TYPE
  SYNTAX DisplayString
  ACCESS read-write
  STATUS mandatory
  DESCRIPTION
    "The 'channel' parameter to the mGuardActionIPsecClear action."
  ::= { mGuardActionIPsecClear 4 }

-- ipsec/up action
mGuardActionIPsecUp OBJECT IDENTIFIER ::= { mGuardActions 15 3 }

-- ipsec/up action status
mGuardActionIPsecUpStatus OBJECT-TYPE
  SYNTAX MGuardActionStatus
  ACCESS read-write
  STATUS mandatory
  DESCRIPTION
    "nph-vpn.cgi?cmd=up

    This object is used is used to prepare or submit the
    mGuardActionIPsecUp action, and to obtain its status."
  ::= { mGuardActionIPsecUp 1 }

-- ipsec/up action result
mGuardActionIPsecUpResult OBJECT-TYPE
  SYNTAX DisplayString
  ACCESS read-only
  STATUS mandatory
  DESCRIPTION
    "After running the mGuardActionIPsecUp action, the result
    can be read from this object."
  ::= { mGuardActionIPsecUp 2 }

-- ipsec/up action name parameter
mGuardActionIPsecUpNameParam OBJECT-TYPE
  SYNTAX DisplayString
  ACCESS read-write
  STATUS mandatory
  DESCRIPTION
    "The 'name' parameter to the mGuardActionIPsecUp action."
  ::= { mGuardActionIPsecUp 3 }

-- ipsec/down action
mGuardActionIPsecDown OBJECT IDENTIFIER ::= { mGuardActions 15 4 }

-- ipsec/down action status
mGuardActionIPsecDownStatus OBJECT-TYPE
  SYNTAX MGuardActionStatus
  ACCESS read-write
  STATUS mandatory
  DESCRIPTION
    "nph-vpn.cgi?cmd=down

    This object is used is used to prepare or submit the
    mGuardActionIPsecDown action, and to obtain its status."
  ::= { mGuardActionIPsecDown 1 }

-- ipsec/down action result
mGuardActionIPsecDownResult OBJECT-TYPE
  SYNTAX DisplayString
  ACCESS read-only
  STATUS mandatory
  DESCRIPTION
    "After running the mGuardActionIPsecDown action, the result
    can be read from this object."
  ::= { mGuardActionIPsecDown 2 }

-- ipsec/down action name parameter
mGuardActionIPsecDownNameParam OBJECT-TYPE
  SYNTAX DisplayString
  ACCESS read-write
  STATUS mandatory
  DESCRIPTION
    "The 'name' parameter to the mGuardActionIPsecDown action."
  ::= { mGuardActionIPsecDown 3 }

-- ipsec/synstat action
mGuardActionIPsecSynStat OBJECT IDENTIFIER ::= { mGuardActions 15 5 }

-- ipsec/synstat action status
mGuardActionIPsecSynStatStatus OBJECT-TYPE
  SYNTAX MGuardActionStatus
  ACCESS read-write
  STATUS mandatory
  DESCRIPTION
    "nph-vpn.cgi?cmd=synstat

    This object is used is used to prepare or submit the
    mGuardActionIPsecSynStat action, and to obtain its status."
  ::= { mGuardActionIPsecSynStat 1 }

-- ipsec/synstat action result
mGuardActionIPsecSynStatResult OBJECT-TYPE
  SYNTAX DisplayString
  ACCESS read-only
  STATUS mandatory
  DESCRIPTION
    "After running the mGuardActionIPsecSynStat action, the result
    can be read from this object."
  ::= { mGuardActionIPsecSynStat 2 }

-- ipsec/synstat action name parameter
mGuardActionIPsecSynStatNameParam OBJECT-TYPE
  SYNTAX DisplayString
  ACCESS read-write
  STATUS mandatory
  DESCRIPTION
    "The 'name' parameter to the mGuardActionIPsecSynStat action."
  ::= { mGuardActionIPsecSynStat 3 }

-- ipsec/synup action
mGuardActionIPsecSynUp OBJECT IDENTIFIER ::= { mGuardActions 15 6 }

-- ipsec/synup action status
mGuardActionIPsecSynUpStatus OBJECT-TYPE
  SYNTAX MGuardActionStatus
  ACCESS read-write
  STATUS mandatory
  DESCRIPTION
    "nph-vpn.cgi?cmd=synup

    This object is used is used to prepare or submit the
    mGuardActionIPsecSynUp action, and to obtain its status."
  ::= { mGuardActionIPsecSynUp 1 }

-- ipsec/synup action result
mGuardActionIPsecSynUpResult OBJECT-TYPE
  SYNTAX DisplayString
  ACCESS read-only
  STATUS mandatory
  DESCRIPTION
    "After running the mGuardActionIPsecSynUp action, the result
    can be read from this object."
  ::= { mGuardActionIPsecSynUp 2 }

-- ipsec/synup action name parameter
mGuardActionIPsecSynUpNameParam OBJECT-TYPE
  SYNTAX DisplayString
  ACCESS read-write
  STATUS mandatory
  DESCRIPTION
    "The 'name' parameter to the mGuardActionIPsecSynUp action."
  ::= { mGuardActionIPsecSynUp 3 }

-- ipsec/syndown action
mGuardActionIPsecSynDown OBJECT IDENTIFIER ::= { mGuardActions 15 7 }

-- ipsec/syndown action status
mGuardActionIPsecSynDownStatus OBJECT-TYPE
  SYNTAX MGuardActionStatus
  ACCESS read-write
  STATUS mandatory
  DESCRIPTION
    "nph-vpn.cgi?cmd=syndown

    This object is used is used to prepare or submit the
    mGuardActionIPsecSynDown action, and to obtain its status."
  ::= { mGuardActionIPsecSynDown 1 }

-- ipsec/syndown action result
mGuardActionIPsecSynDownResult OBJECT-TYPE
  SYNTAX DisplayString
  ACCESS read-only
  STATUS mandatory
  DESCRIPTION
    "After running the mGuardActionIPsecSynDown action, the result
    can be read from this object."
  ::= { mGuardActionIPsecSynDown 2 }

-- ipsec/syndown action name parameter
mGuardActionIPsecSynDownNameParam OBJECT-TYPE
  SYNTAX DisplayString
  ACCESS read-write
  STATUS mandatory
  DESCRIPTION
    "The 'name' parameter to the mGuardActionIPsecSynDown action."
  ::= { mGuardActionIPsecSynDown 3 }

-- bladectrl/push-config action
mGuardActionBladePushConfig OBJECT IDENTIFIER ::= { mGuardActions 16 1 }

-- bladectrl/push-config action status
mGuardActionBladePushConfigStatus OBJECT-TYPE
  SYNTAX MGuardActionStatus
  ACCESS read-write
  STATUS mandatory
  DESCRIPTION
    "Restores the configuration profile from the Blade Controller
    to the designated Blade and applies it.
    This action is only valid on Blade Controller devices.

    This object is used is used to prepare or submit the
    mGuardActionBladePushConfig action, and to obtain its status."
  ::= { mGuardActionBladePushConfig 1 }

-- bladectrl/push-config action result
mGuardActionBladePushConfigResult OBJECT-TYPE
  SYNTAX DisplayString
  ACCESS read-only
  STATUS mandatory
  DESCRIPTION
    "After running the mGuardActionBladePushConfig action, the result
    can be read from this object."
  ::= { mGuardActionBladePushConfig 2 }

-- bladectrl/push-config action name parameter
mGuardActionBladePushConfigNameParam OBJECT-TYPE
  SYNTAX DisplayString
  ACCESS read-write
  STATUS mandatory
  DESCRIPTION
    "The 'name' parameter to the mGuardActionBladePushConfig action."
  ::= { mGuardActionBladePushConfig 3 }

-- bladectrl/pull-config action
mGuardActionBladePullConfig OBJECT IDENTIFIER ::= { mGuardActions 16 2 }

-- bladectrl/pull-config action status
mGuardActionBladePullConfigStatus OBJECT-TYPE
  SYNTAX MGuardActionStatus
  ACCESS read-write
  STATUS mandatory
  DESCRIPTION
    "Makes a configuration backup of the designated Blade.
    This action is only valid on Blade Controller devices.

    This object is used is used to prepare or submit the
    mGuardActionBladePullConfig action, and to obtain its status."
  ::= { mGuardActionBladePullConfig 1 }

-- bladectrl/pull-config action result
mGuardActionBladePullConfigResult OBJECT-TYPE
  SYNTAX DisplayString
  ACCESS read-only
  STATUS mandatory
  DESCRIPTION
    "After running the mGuardActionBladePullConfig action, the result
    can be read from this object."
  ::= { mGuardActionBladePullConfig 2 }

-- bladectrl/pull-config action name parameter
mGuardActionBladePullConfigNameParam OBJECT-TYPE
  SYNTAX DisplayString
  ACCESS read-write
  STATUS mandatory
  DESCRIPTION
    "The 'name' parameter to the mGuardActionBladePullConfig action."
  ::= { mGuardActionBladePullConfig 3 }

-- bladectrl/delete-config action
mGuardActionBladeDeleteConfig OBJECT IDENTIFIER ::= { mGuardActions 16 3 }

-- bladectrl/delete-config action status
mGuardActionBladeDeleteConfigStatus OBJECT-TYPE
  SYNTAX MGuardActionStatus
  ACCESS read-write
  STATUS mandatory
  DESCRIPTION
    "Deletes the configuration backup of the designated Blade.
    This action is only valid on Blade Controller devices.

    This object is used is used to prepare or submit the
    mGuardActionBladeDeleteConfig action, and to obtain its status."
  ::= { mGuardActionBladeDeleteConfig 1 }

-- bladectrl/delete-config action result
mGuardActionBladeDeleteConfigResult OBJECT-TYPE
  SYNTAX DisplayString
  ACCESS read-only
  STATUS mandatory
  DESCRIPTION
    "After running the mGuardActionBladeDeleteConfig action, the result
    can be read from this object."
  ::= { mGuardActionBladeDeleteConfig 2 }

-- bladectrl/delete-config action name parameter
mGuardActionBladeDeleteConfigNameParam OBJECT-TYPE
  SYNTAX DisplayString
  ACCESS read-write
  STATUS mandatory
  DESCRIPTION
    "The 'name' parameter to the mGuardActionBladeDeleteConfig action."
  ::= { mGuardActionBladeDeleteConfig 3 }

-- /blade/slotid eds object
  mGuardBladeSlotIdEds OBJECT-TYPE
  SYNTAX INTEGER
  ACCESS read-only
  STATUS mandatory
  DESCRIPTION
      "Slot ID of this device on the blade rack"
  ::= { mGuardEDS 100 }

-- /blade/rackid eds object
  mGuardBladeRackIdEds OBJECT-TYPE
  SYNTAX INTEGER
  ACCESS read-only
  STATUS mandatory
  DESCRIPTION
      "Rack ID of the blade"
  ::= { mGuardEDS 101 }

-- /ecs/status eds object
  mGuardEDSEcsStatus OBJECT-TYPE
  SYNTAX INTEGER {
        notPresent (1),
        removed (2),
        ok (3),
        notInSync (4),
        genericErr (8)
  }
  ACCESS read-only
  STATUS mandatory
  DESCRIPTION
      "State of the ECS"
  ::= { mGuardEDS 3 }

-- /gps/north eds object
  mGuardEDSGpsNorth OBJECT-TYPE
  SYNTAX DisplayString
  ACCESS read-only
  STATUS mandatory
  DESCRIPTION
      "Latitude of the current position"
  ::= { mGuardEDS 4 }

-- /gps/east eds object
  mGuardEDSGpsEast OBJECT-TYPE
  SYNTAX DisplayString
  ACCESS read-only
  STATUS mandatory
  DESCRIPTION
      "Longitude of the current position"
  ::= { mGuardEDS 5 }

-- /gps/valid eds object
  mGuardEDSGpsValid OBJECT-TYPE
  SYNTAX INTEGER {
        no (1),
        yes (2)
  }
  ACCESS read-only
  STATUS mandatory
  DESCRIPTION
      "Validity of the positional data"
  ::= { mGuardEDS 6 }

-- /gps/satellites eds object
  mGuardEDSGpsSatellites OBJECT-TYPE
  SYNTAX INTEGER
  ACCESS read-only
  STATUS mandatory
  DESCRIPTION
      "Number of satellites"
  ::= { mGuardEDS 7 }

-- /gsm/incoming_sms eds object
  mGuardEDSGsmIncomingSMS OBJECT-TYPE
  SYNTAX DisplayString
  ACCESS read-only
  STATUS mandatory
  DESCRIPTION
      "Telephone number and message of the last incoming text message"
  ::= { mGuardEDS 9 }

-- /gsm/roaming eds object
  mGuardEDSGsmRoaming OBJECT-TYPE
  SYNTAX INTEGER {
        no (1),
        yes (2),
        unknown (3)
  }
  ACCESS read-only
  STATUS mandatory
  DESCRIPTION
      "Roaming state of the mobile network engine"
  ::= { mGuardEDS 10 }

-- /gsm/service eds object
  mGuardEDSGsmService OBJECT-TYPE
  SYNTAX INTEGER {
        no (1),
        yes (2)
  }
  ACCESS read-only
  STATUS mandatory
  DESCRIPTION
      "Registration state to the mobile network"
  ::= { mGuardEDS 11 }

-- /gsm/signallevel eds object
  mGuardEDSGsmSignallevel OBJECT-TYPE
  SYNTAX DisplayString
  ACCESS read-only
  STATUS mandatory
  DESCRIPTION
      "Signal level"
  ::= { mGuardEDS 12 }

-- /gsm/selected_sim eds object
  mGuardEDSGsmSelectedSIM OBJECT-TYPE
  SYNTAX INTEGER {
        sim1 (1),
        sim2 (2),
        none (3)
  }
  ACCESS read-only
  STATUS mandatory
  DESCRIPTION
      "Currently selected SIM slot"
  ::= { mGuardEDS 13 }

-- /gsm/simstatus eds object
  mGuardEDSGsmSIMStatus OBJECT-TYPE
  SYNTAX INTEGER {
        removed (1),
        inserted (2),
        invalid (3),
        initialized (4),
        unknown (5)
  }
  ACCESS read-only
  STATUS mandatory
  DESCRIPTION
      "Status of the currenly used SIM"
  ::= { mGuardEDS 14 }

-- /gsm/sim1/status eds object
  mGuardEDSGsmSIMStatusSIM1 OBJECT-TYPE
  SYNTAX INTEGER {
        unknown (-1),
        removed (1),
        inserted (2),
        wrongPin (3),
        pinNeeded (4),
        pukNeeded (5),
        error (6),
        ready (7),
        empty (8)
  }
  ACCESS read-only
  STATUS mandatory
  DESCRIPTION
      "State of the primary SIM"
  ::= { mGuardEDS 15 }

-- /gsm/sim2/status eds object
  mGuardEDSGsmSIMStatusSIM2 OBJECT-TYPE
  SYNTAX INTEGER {
        unknown (-1),
        removed (1),
        inserted (2),
        wrongPin (3),
        pinNeeded (4),
        pukNeeded (5),
        error (6),
        ready (7),
        empty (8)
  }
  ACCESS read-only
  STATUS mandatory
  DESCRIPTION
      "State of the secondary SIM"
  ::= { mGuardEDS 16 }

-- /gsm/sim1/apn eds object
  mGuardEDSGsmAPNSIM1 OBJECT-TYPE
  SYNTAX DisplayString
  ACCESS read-only
  STATUS mandatory
  DESCRIPTION
      "last used APN of SIM1"
  ::= { mGuardEDS 102 }

-- /gsm/sim2/apn eds object
  mGuardEDSGsmAPNSIM2 OBJECT-TYPE
  SYNTAX DisplayString
  ACCESS read-only
  STATUS mandatory
  DESCRIPTION
      "last used APN of SIM2"
  ::= { mGuardEDS 103 }

-- /gsm/sim1/ppp_last_uptime eds object
  mGuardEDSGsmPPPuptime1 OBJECT-TYPE
  SYNTAX DisplayString
  ACCESS read-only
  STATUS mandatory
  DESCRIPTION
      "last mobile data dialup time for sim1"
  ::= { mGuardEDS 104 }

-- /gsm/sim1/ppp_next_interval eds object
  mGuardEDSGsmPPPinterval1 OBJECT-TYPE
  SYNTAX DisplayString
  ACCESS read-only
  STATUS mandatory
  DESCRIPTION
      "next mobile data dialup wait in minutes on sim1"
  ::= { mGuardEDS 105 }

-- /gsm/sim1/cnum eds object
  mGuardEDSGsmCNUMSIM1 OBJECT-TYPE
  SYNTAX DisplayString
  ACCESS read-only
  STATUS mandatory
  DESCRIPTION
      "telephone number of SIM1"
  ::= { mGuardEDS 106 }

-- /gsm/sim2/cnum eds object
  mGuardEDSGsmCNUMSIM2 OBJECT-TYPE
  SYNTAX DisplayString
  ACCESS read-only
  STATUS mandatory
  DESCRIPTION
      "telephone number of SIM2"
  ::= { mGuardEDS 107 }

-- /gsm/sim1/apn_ota_status eds object
  mGuardEDSGsmAPNOtaStatusSIM1 OBJECT-TYPE
  SYNTAX DisplayString
  ACCESS read-only
  STATUS mandatory
  DESCRIPTION
      "Status of SIM1 APN provisioning"
  ::= { mGuardEDS 108 }

-- /gsm/sim2/apn_ota_status eds object
  mGuardEDSGsmAPNOtaStatusSIM2 OBJECT-TYPE
  SYNTAX DisplayString
  ACCESS read-only
  STATUS mandatory
  DESCRIPTION
      "Status of SIM2 APN provisioning"
  ::= { mGuardEDS 109 }

-- /gsm/rsm/status eds object
  mGuardEDSGsmRsmStatus OBJECT-TYPE
  SYNTAX INTEGER {
        uninitialized (1),
        initializing (2),
        switchingPrimarySim (3),
        unlockingPrimarySim (4),
        switchingSecondarySim (5),
        unlockingSecondarySim (6),
        connectingToVoiceNetwork (7),
        connected (8),
        connectingToDataNetwork (9),
        online (10),
        error (11),
        verizonLteOta (12)
  }
  ACCESS read-only
  STATUS mandatory
  DESCRIPTION
      "State of the mobile network interface"
  ::= { mGuardEDS 96 }

-- /gsm/tray1/status eds object
  mGuardEDSGsmSIMTrayStatusTray1 OBJECT-TYPE
  SYNTAX INTEGER {
        removed (1),
        inserted (2)
  }
  ACCESS read-only
  STATUS mandatory
  DESCRIPTION
      "Status of the SIM tray in slot 1"
  ::= { mGuardEDS 90 }

-- /gsm/tray2/status eds object
  mGuardEDSGsmSIMTrayStatusTray2 OBJECT-TYPE
  SYNTAX INTEGER {
        removed (1),
        inserted (2)
  }
  ACCESS read-only
  STATUS mandatory
  DESCRIPTION
      "Status of the SIM tray in slot 2"
  ::= { mGuardEDS 84 }

-- /gsm/power eds object
  mGuardEDSGsmPower OBJECT-TYPE
  SYNTAX INTEGER {
        off (1),
        on (2)
  }
  ACCESS read-only
  STATUS mandatory
  DESCRIPTION
      "Power state of the mobile network engine"
  ::= { mGuardEDS 17 }

-- /gsm/radio eds object
  mGuardEDSGsmRadio OBJECT-TYPE
  SYNTAX INTEGER {
        off (1),
        on (2),
        unknown (3)
  }
  ACCESS read-only
  STATUS mandatory
  DESCRIPTION
      "State of the modem radio"
  ::= { mGuardEDS 89 }

-- /gsm/operator eds object
  mGuardEDSGsmOperator OBJECT-TYPE
  SYNTAX DisplayString
  ACCESS read-only
  STATUS mandatory
  DESCRIPTION
      "Currently used mobile network operator"
  ::= { mGuardEDS 35 }

-- /gsm/lac eds object
  mGuardEDSGsmLAC OBJECT-TYPE
  SYNTAX DisplayString
  ACCESS read-only
  STATUS mandatory
  DESCRIPTION
      "Location Area Code (LAC) of the base station"
  ::= { mGuardEDS 36 }

-- /gsm/cid eds object
  mGuardEDSGsmCID OBJECT-TYPE
  SYNTAX DisplayString
  ACCESS read-only
  STATUS mandatory
  DESCRIPTION
      "Cell ID (CID) of the base station"
  ::= { mGuardEDS 37 }

-- /gsm/cown eds object
  mGuardEDSGsmCellOwn OBJECT-TYPE
  SYNTAX DisplayString
  ACCESS read-only
  STATUS mandatory
  DESCRIPTION
      "Public Land Mobile Network (PLMN) of the base station"
  ::= { mGuardEDS 40 }

-- /gsm/rat eds object
  mGuardEDSGsmRat OBJECT-TYPE
  SYNTAX INTEGER {
        none (-2),
        unknown (-1),
        gsmGPRS (1),
        gsmEGPRS (2),
        utran (3),
        cdmaRTT (6),
        cdmaEVDOr0 (7),
        cdmaEVDOrA (8),
        utranHSDPA (9),
        utranHSUPA (10),
        utranHSDPAaHSUPA (11),
        cdmaEVDOrB (12),
        ehrpd (13),
        lte (14),
        utranHSPAP (15),
        gsm (16),
        cdmaTDS (17)
  }
  ACCESS read-only
  STATUS mandatory
  DESCRIPTION
      "Mobile Network Radio Access Technology"
  ::= { mGuardEDS 83 }

-- /gsm/cdma_sid eds object
  mGuardEDSCdmaSid OBJECT-TYPE
  SYNTAX DisplayString
  ACCESS read-only
  STATUS mandatory
  DESCRIPTION
      "Mobile network cdma2000 System ID"
  ::= { mGuardEDS 51 }

-- /gsm/cdma_nid eds object
  mGuardEDSCdmaNid OBJECT-TYPE
  SYNTAX DisplayString
  ACCESS read-only
  STATUS mandatory
  DESCRIPTION
      "Mobile network cdma2000 Network ID"
  ::= { mGuardEDS 52 }

-- /gsm/cdma_mdn eds object
  mGuardEDSCdmaMobileDirectoryNumber OBJECT-TYPE
  SYNTAX DisplayString
  ACCESS read-only
  STATUS mandatory
  DESCRIPTION
      "Mobile network cdma2000 Directory Number"
  ::= { mGuardEDS 53 }

-- /gsm/cdma_otasp eds object
  mGuardEDSCdmaOTASP OBJECT-TYPE
  SYNTAX INTEGER {
        request (1),
        register (2),
        registered (3),
        failed (4),
        unregistered (5)
  }
  ACCESS read-only
  STATUS mandatory
  DESCRIPTION
      "Mobile network cdma2000 OTASP Registration"
  ::= { mGuardEDS 54 }

-- /gsm/sim_fallback eds object
  mGuardEDSSIMFallback OBJECT-TYPE
  SYNTAX INTEGER {
        no (1),
        yes (2)
  }
  ACCESS read-only
  STATUS mandatory
  DESCRIPTION
      "Mobile network fallback SIM activity"
  ::= { mGuardEDS 39 }

-- /gsm/network_probe eds object
  mGuardEDSGsmNetworkProbe OBJECT-TYPE
  SYNTAX INTEGER {
        disabled (1),
        enabled (2),
        failed (3),
        succeeded (4)
  }
  ACCESS read-only
  STATUS mandatory
  DESCRIPTION
      "Mobile network probes"
  ::= { mGuardEDS 49 }

-- /gsm/outgoing_sms eds object
  mGuardEDSGsmOutgoingSMS OBJECT-TYPE
  SYNTAX DisplayString
  ACCESS read-only
  STATUS mandatory
  DESCRIPTION
      "Telephone number and message of the last outgoing text message"
  ::= { mGuardEDS 59 }

-- /gsm/outgoing_sms_status eds object
  mGuardEDSGsmOutgoingSMSStatus OBJECT-TYPE
  SYNTAX INTEGER {
        scheduled (1),
        success (2),
        failure (3)
  }
  ACCESS read-only
  STATUS mandatory
  DESCRIPTION
      "State of the last outgoing text message"
  ::= { mGuardEDS 60 }

-- /gsm/modem_temp eds object
  mGuardEDSGsmModemTemperature OBJECT-TYPE
  SYNTAX INTEGER {
        normal (1),
        high (2),
        highCritical (3),
        low (4),
        lowCritical (5),
        unavailable (6)
  }
  ACCESS read-only
  STATUS mandatory
  DESCRIPTION
      "Temperature state of the modem"
  ::= { mGuardEDS 85 }

-- /gsm/data_call_state eds object
  mGuardEDSGsmDataCallState OBJECT-TYPE
  SYNTAX INTEGER  ACCESS read-only
  STATUS mandatory
  DESCRIPTION
      "Data call active(1)/inactive(0) state and CID of active data call"
  ::= { mGuardEDS 86 }

-- /gsm/imei eds object
  mGuardEDSGsmIMEI OBJECT-TYPE
  SYNTAX INTEGER  ACCESS read-only
  STATUS mandatory
  DESCRIPTION
      "International Mobile Equipment Identifier (IMEI)"
  ::= { mGuardEDS 87 }

-- /gsm/meid eds object
  mGuardEDSGsmMEID OBJECT-TYPE
  SYNTAX INTEGER  ACCESS read-only
  STATUS mandatory
  DESCRIPTION
      "Mobile Equipment Identifier (MEID)"
  ::= { mGuardEDS 88 }

-- /ihal/contact eds object
  mGuardEDSAlarmContact OBJECT-TYPE
  SYNTAX INTEGER {
        close (1),
        open (2)
  }
  ACCESS read-only
  STATUS mandatory
  DESCRIPTION
      "State of the alarm output"
  ::= { mGuardEDS 18 }

-- /ihal/contactreason eds object
  mGuardEDSAlarmContactReason OBJECT-TYPE
  SYNTAX INTEGER {
        noAlarm (1),
        linkExt (2),
        linkInt (3),
        psu1 (4),
        psu2 (5),
        temp (6),
        ccheck (7),
        modem (8),
        linkSwp0 (9),
        linkSwp1 (10),
        linkSwp2 (11),
        linkSwp3 (12),
        linkSwp4 (13),
        linkDmz (14)
  }
  ACCESS read-only
  STATUS mandatory
  DESCRIPTION
      "Reason for activating the alarm output"
  ::= { mGuardEDS 19 }

-- /ihal/power/psu1 eds object
  mGuardEDSPowerPSU1 OBJECT-TYPE
  SYNTAX INTEGER {
        ok (1),
        fail (2)
  }
  ACCESS read-only
  STATUS mandatory
  DESCRIPTION
      "State of the power supply 1"
  ::= { mGuardEDS 20 }

-- /ihal/power/psu2 eds object
  mGuardEDSPowerPSU2 OBJECT-TYPE
  SYNTAX INTEGER {
        ok (1),
        fail (2)
  }
  ACCESS read-only
  STATUS mandatory
  DESCRIPTION
      "State of the power supply 2"
  ::= { mGuardEDS 21 }

-- /ihal/service/cmd1 eds object
  mGuardEDSServiceInput1 OBJECT-TYPE
  SYNTAX INTEGER {
        on (1),
        off (2)
  }
  ACCESS read-only
  STATUS mandatory
  DESCRIPTION
      "State of the input/CMD 1"
  ::= { mGuardEDS 22 }

-- /ihal/service/cmd2 eds object
  mGuardEDSServiceInput2 OBJECT-TYPE
  SYNTAX INTEGER {
        on (1),
        off (2)
  }
  ACCESS read-only
  STATUS mandatory
  DESCRIPTION
      "State of the input/CMD 2"
  ::= { mGuardEDS 23 }

-- /ihal/service/cmd3 eds object
  mGuardEDSServiceInput3 OBJECT-TYPE
  SYNTAX INTEGER {
        on (1),
        off (2)
  }
  ACCESS read-only
  STATUS mandatory
  DESCRIPTION
      "State of the input/CMD 3"
  ::= { mGuardEDS 24 }

-- /ihal/temperature/temp_board eds object
  mGuardEDSBoardTemperature OBJECT-TYPE
  SYNTAX DisplayString
  ACCESS read-only
  STATUS mandatory
  DESCRIPTION
      "Board temperature"
  ::= { mGuardEDS 47 }

-- /ihal/temperature/temp_cpu eds object
  mGuardEDSCPUTemperature OBJECT-TYPE
  SYNTAX DisplayString
  ACCESS read-only
  STATUS mandatory
  DESCRIPTION
      "CPU temperature"
  ::= { mGuardEDS 48 }

-- /ihal/temperature/temp_board_alarm eds object
  mGuardEDSBoardTemperatureState OBJECT-TYPE
  SYNTAX INTEGER {
        ok (1),
        hot (2),
        cold (3)
  }
  ACCESS read-only
  STATUS mandatory
  DESCRIPTION
      "Board temperature state"
  ::= { mGuardEDS 25 }

-- /ihal/temperature/temp_cpu_alarm eds object
  mGuardEDSCpuTemperatureState OBJECT-TYPE
  SYNTAX INTEGER {
        ok (1),
        hot (2),
        cold (3)
  }
  ACCESS read-only
  STATUS mandatory
  DESCRIPTION
      "CPU temperature state"
  ::= { mGuardEDS 61 }

-- /ihal/fan/fan1 eds object
  mGuardEDSFan1 OBJECT-TYPE
  SYNTAX DisplayString
  ACCESS read-only
  STATUS mandatory
  DESCRIPTION
      "Fan 1 RPM"
  ::= { mGuardEDS 62 }

-- /ihal/fan/fan2 eds object
  mGuardEDSFan2 OBJECT-TYPE
  SYNTAX DisplayString
  ACCESS read-only
  STATUS mandatory
  DESCRIPTION
      "Fan 2 RPM"
  ::= { mGuardEDS 63 }

-- /ihal/fan/fan3 eds object
  mGuardEDSFan3 OBJECT-TYPE
  SYNTAX DisplayString
  ACCESS read-only
  STATUS mandatory
  DESCRIPTION
      "Fan 3 RPM"
  ::= { mGuardEDS 64 }

-- /ihal/fan/fan4 eds object
  mGuardEDSFan4 OBJECT-TYPE
  SYNTAX DisplayString
  ACCESS read-only
  STATUS mandatory
  DESCRIPTION
      "Fan 4 RPM"
  ::= { mGuardEDS 65 }

-- /ihal/fan/fan5 eds object
  mGuardEDSFan5 OBJECT-TYPE
  SYNTAX DisplayString
  ACCESS read-only
  STATUS mandatory
  DESCRIPTION
      "Fan 5 RPM"
  ::= { mGuardEDS 66 }

-- /ihal/fan/fan1_alarm eds object
  mGuardEDSFan1State OBJECT-TYPE
  SYNTAX INTEGER {
        ok (1),
        high (2),
        low (3)
  }
  ACCESS read-only
  STATUS mandatory
  DESCRIPTION
      "Fan 1 speed state"
  ::= { mGuardEDS 67 }

-- /ihal/fan/fan2_alarm eds object
  mGuardEDSFan2State OBJECT-TYPE
  SYNTAX INTEGER {
        ok (1),
        high (2),
        low (3)
  }
  ACCESS read-only
  STATUS mandatory
  DESCRIPTION
      "Fan 2 speed state"
  ::= { mGuardEDS 68 }

-- /ihal/fan/fan3_alarm eds object
  mGuardEDSFan3State OBJECT-TYPE
  SYNTAX INTEGER {
        ok (1),
        high (2),
        low (3)
  }
  ACCESS read-only
  STATUS mandatory
  DESCRIPTION
      "Fan 3 speed state"
  ::= { mGuardEDS 69 }

-- /ihal/fan/fan4_alarm eds object
  mGuardEDSFan4State OBJECT-TYPE
  SYNTAX INTEGER {
        ok (1),
        high (2),
        low (3)
  }
  ACCESS read-only
  STATUS mandatory
  DESCRIPTION
      "Fan 4 speed state"
  ::= { mGuardEDS 70 }

-- /ihal/fan/fan5_alarm eds object
  mGuardEDSFan5State OBJECT-TYPE
  SYNTAX INTEGER {
        ok (1),
        high (2),
        low (3)
  }
  ACCESS read-only
  STATUS mandatory
  DESCRIPTION
      "Fan 5 speed state"
  ::= { mGuardEDS 71 }

-- /network/autostealth/ip eds object
  mGuardEDSAutoStealthIP OBJECT-TYPE
  SYNTAX IpAddress
  ACCESS read-only
  STATUS mandatory
  DESCRIPTION
      "Learned IP address of automatic stealth mode"
  ::= { mGuardEDS 26 }

-- /network/autostealth/mac eds object
  mGuardEDSAutoStealthMAC OBJECT-TYPE
  SYNTAX DisplayString
  ACCESS read-only
  STATUS mandatory
  DESCRIPTION
      "Learned MAC address of automatic stealth mode"
  ::= { mGuardEDS 27 }

-- /network/autostealth/br_if eds object
  mGuardEDSAutoStealthBridgeIF OBJECT-TYPE
  SYNTAX DisplayString
  ACCESS read-only
  STATUS mandatory
  DESCRIPTION
      "Bridge interface of automatic stealth mode"
  ::= { mGuardEDS 73 }

-- /network/autostealth/dns_ip eds object
  mGuardEDSAutoStealthDnsIP OBJECT-TYPE
  SYNTAX DisplayString
  ACCESS read-only
  STATUS mandatory
  DESCRIPTION
      "Learned DNS server IP"
  ::= { mGuardEDS 99 }

-- /network/ext2up eds object
  mGuardEDSExt2TemporaryUp OBJECT-TYPE
  SYNTAX INTEGER {
        no (1),
        yes (2)
  }
  ACCESS read-only
  STATUS mandatory
  DESCRIPTION
      "Temporary state of the secondary external interface"
  ::= { mGuardEDS 28 }

-- /network/modem/state eds object
  mGuardEDSModemState OBJECT-TYPE
  SYNTAX INTEGER {
        offline (1),
        dialing (2),
        online (3),
        init (4)
  }
  ACCESS read-only
  STATUS mandatory
  DESCRIPTION
      "Modem network connection state"
  ::= { mGuardEDS 41 }

-- /network/initialized eds object
  mGuardEDSNetworkInitialized OBJECT-TYPE
  SYNTAX INTEGER {
        no (1),
        yes (2)
  }
  ACCESS read-only
  STATUS mandatory
  DESCRIPTION
      "Whether the network is setup during boot"
  ::= { mGuardEDS 50 }

-- /network/ntp_state eds object
  mGuardEDSNetworkNTPState OBJECT-TYPE
  SYNTAX INTEGER {
        disabled (1),
        notSynced (2),
        synchronized (3)
  }
  ACCESS read-only
  STATUS mandatory
  DESCRIPTION
      "NTP time synchronization state"
  ::= { mGuardEDS 31 }

-- /redundancy/boot-complete eds object
  mGuardEDSRedundancyBootComplete OBJECT-TYPE
  SYNTAX INTEGER {
        no (1),
        yes (2)
  }
  ACCESS read-only
  STATUS mandatory
  DESCRIPTION
      "Status of the boot process for the redundancy subsystem"
  ::= { mGuardEDS 30 }

-- /redundancy/status eds object
  mGuardEDSRedundancyStatus OBJECT-TYPE
  SYNTAX INTEGER {
        booting (1),
        faulty (2),
        faultyWaiting (3),
        outdated (4),
        outdatedWaiting (5),
        onStandby (6),
        onStandbyWaiting (7),
        becomesActive (8),
        active (9),
        activeWaiting (10),
        becomesStandby (11)
  }
  ACCESS read-only
  STATUS mandatory
  DESCRIPTION
      "Status of redundancy"
  ::= { mGuardEDS 33 }

-- /redundancy/cc/ext1/ok eds object
  mGuardEDSRedundancyCcExt1Ok OBJECT-TYPE
  SYNTAX INTEGER {
        no (1),
        yes (2)
  }
  ACCESS read-only
  STATUS mandatory
  DESCRIPTION
      "Connectivity check result of the external interface"
  ::= { mGuardEDS 92 }

-- /redundancy/cc/ext1/state eds object
  mGuardEDSRedundancyCcExt1State OBJECT-TYPE
  SYNTAX INTEGER {
        nolink (1),
        link (2),
        primary (3),
        secondary (4)
  }
  ACCESS read-only
  STATUS mandatory
  DESCRIPTION
      "Connectivity check state of the external interface"
  ::= { mGuardEDS 93 }

-- /redundancy/cc/int/ok eds object
  mGuardEDSRedundancyCcIntOk OBJECT-TYPE
  SYNTAX INTEGER {
        no (1),
        yes (2)
  }
  ACCESS read-only
  STATUS mandatory
  DESCRIPTION
      "Connectivity check result of the internal interface"
  ::= { mGuardEDS 94 }

-- /redundancy/cc/int/state eds object
  mGuardEDSRedundancyCcIntState OBJECT-TYPE
  SYNTAX INTEGER {
        nolink (1),
        link (2),
        primary (3),
        secondary (4)
  }
  ACCESS read-only
  STATUS mandatory
  DESCRIPTION
      "Connectivity check state of the internal interface"
  ::= { mGuardEDS 95 }

-- /system/time_sync eds object
  mGuardEDSSystemTimeSync OBJECT-TYPE
  SYNTAX INTEGER {
        notSynced (1),
        manually (2),
        stamp (3),
        rtc (4),
        ntp (5),
        gps (6),
        gpslost (7)
  }
  ACCESS read-only
  STATUS mandatory
  DESCRIPTION
      "State of the system time synchronization"
  ::= { mGuardEDS 34 }

-- /system/dnscache eds object
  mGuardEDSDnsCacheState OBJECT-TYPE
  SYNTAX INTEGER {
        down (1),
        up (2)
  }
  ACCESS read-only
  STATUS mandatory
  DESCRIPTION
      "State of the DNS resolver"
  ::= { mGuardEDS 42 }

-- /system/subagent eds object
  mGuardEDSSubagent OBJECT-TYPE
  SYNTAX INTEGER {
        down (1),
        up (2)
  }
  ACCESS read-only
  STATUS mandatory
  DESCRIPTION
      "State of the SNMP subagent"
  ::= { mGuardEDS 45 }

-- /system/update_running eds object
  mGuardEDSSystemUpdateRunning OBJECT-TYPE
  SYNTAX DisplayString
  ACCESS read-only
  STATUS mandatory
  DESCRIPTION
      "Name of the currently running update"
  ::= { mGuardEDS 91 }

-- /system/user_login eds object
  mGuardEDSSystemUserLogin OBJECT-TYPE
  SYNTAX INTEGER {
        disabled (1),
        login (2),
        logout (3)
  }
  ACCESS read-only
  STATUS mandatory
  DESCRIPTION
      "Login state of the user"
  ::= { mGuardEDS 82 }

-- /system/cert_enroll/state eds object
  mGuardEDSSystemCertEnrollState OBJECT-TYPE
  SYNTAX INTEGER {
        absent (1),
        expired (2),
        valid (3),
        renewing (4),
        notyetvalid (5),
        error (6),
        notimesync (7)
  }
  ACCESS read-only
  STATUS mandatory
  DESCRIPTION
      "State of the enrolled certificate"
  ::= { mGuardEDS 97 }

-- /system/cert_enroll/expires eds object
  mGuardEDSSystemCertEnrollValid OBJECT-TYPE
  SYNTAX DisplayString
  ACCESS read-only
  STATUS mandatory
  DESCRIPTION
      "Expiration date of the enrolled certificate"
  ::= { mGuardEDS 98 }

-- /vpn/license_used eds object
  mGuardEDSVPNLicense OBJECT-TYPE
  SYNTAX INTEGER
  ACCESS read-only
  STATUS mandatory
  DESCRIPTION
      "VPN license counter"
  ::= { mGuardEDS 75 }

-- /network/dns-servers eds object
  mGuardEDSDnsServers OBJECT-TYPE
  SYNTAX DisplayString
  ACCESS read-only
  STATUS mandatory
  DESCRIPTION
      "Used DNS servers"
  ::= { mGuardEDS 55 }

-- /network/defaultroute eds object
  mGuardEDSDefaultroute OBJECT-TYPE
  SYNTAX DisplayString
  ACCESS read-only
  STATUS mandatory
  DESCRIPTION
      "Current default route"
  ::= { mGuardEDS 56 }

-- /network/dyndns eds object
  mGuardEDSDynDns OBJECT-TYPE
  SYNTAX INTEGER {
        disabled (1),
        trying (2),
        success (3),
        failure (4)
  }
  ACCESS read-only
  STATUS mandatory
  DESCRIPTION
      "State of the dyndns registration"
  ::= { mGuardEDS 57 }

-- /network/dyndns-msg eds object
  mGuardEDSDynDnsMsg OBJECT-TYPE
  SYNTAX DisplayString
  ACCESS read-only
  STATUS mandatory
  DESCRIPTION
      "Status message"
  ::= { mGuardEDS 58 }

-- /openvpn/license_used eds object
  mGuardEDSOpenVPNLicense OBJECT-TYPE
  SYNTAX INTEGER
  ACCESS read-only
  STATUS mandatory
  DESCRIPTION
      "OpenVPN license counter"
  ::= { mGuardEDS 74 }

-- /mai/changed/time eds object
  maiChangeTime OBJECT-TYPE
  SYNTAX DisplayString
  ACCESS read-only
  STATUS mandatory
  DESCRIPTION
      "Seconds since Epoch of the last commit"
  ::= { mGuardEDS 76 }

-- /mai/changed/user eds object
  maiChangeUser OBJECT-TYPE
  SYNTAX DisplayString
  ACCESS read-only
  STATUS mandatory
  DESCRIPTION
      "User name of the last MAI commit"
  ::= { mGuardEDS 77 }

-- /mai/changed/role eds object
  maiChangeRole OBJECT-TYPE
  SYNTAX DisplayString
  ACCESS read-only
  STATUS mandatory
  DESCRIPTION
      "Role name of the last MAI commit"
  ::= { mGuardEDS 78 }

-- /mai/changed/config_hash eds object
  maiChangeConfigHash OBJECT-TYPE
  SYNTAX DisplayString
  ACCESS read-only
  STATUS mandatory
  DESCRIPTION
      "Hashsum of the last MAI commit"
  ::= { mGuardEDS 79 }

-- /mai/changed/milestone eds object
  maiChangeMilestone OBJECT-TYPE
  SYNTAX DisplayString
  ACCESS read-only
  STATUS mandatory
  DESCRIPTION
      "MAI configuration milestone"
  ::= { mGuardEDS 80 }

-- /mai/reconfiguring eds object
  maiReconfig OBJECT-TYPE
  SYNTAX INTEGER {
        idle (1),
        reconfig (2)
  }
  ACCESS read-only
  STATUS mandatory
  DESCRIPTION
      "System reconfiguration"
  ::= { mGuardEDS 81 }

mGuardNTPStatus OBJECT-TYPE
  SYNTAX DisplayString
  ACCESS read-only
  STATUS mandatory
  DESCRIPTION
    "NTP state"
  ::= { mGuardNTP 5 }

mGuardSNMPError OBJECT-TYPE
  SYNTAX DisplayString
  ACCESS read-only
  STATUS mandatory
  DESCRIPTION
    "Field, providing textual description of errors caused by SNMP
    operations."
  ::= { mGuardb 8 }

   mGuardNetworkStatMode OBJECT-TYPE
     SYNTAX DisplayString
     ACCESS read-only
     STATUS mandatory
     DESCRIPTION
      "Current network mode of this device."
    ::= { mGuardNetworkStatus 1 }

    mGuardNetworkStatExtIP OBJECT-TYPE
     SYNTAX DisplayString
     ACCESS read-only
     STATUS mandatory
     DESCRIPTION
      "external IP address of this device."
    ::= { mGuardNetworkStatus 2 }

   mGuardNetworkStatGateway OBJECT-TYPE
     SYNTAX DisplayString
     ACCESS read-only
     STATUS mandatory
     DESCRIPTION
      "Default gateway via the external IP address."
    ::= { mGuardNetworkStatus 3 }

   mGuardNetworkStatDynIPReg OBJECT-TYPE
     SYNTAX DisplayString
     ACCESS read-only
     STATUS mandatory
     DESCRIPTION
      "Statistics about VPN DynIP registration."
    ::= { mGuardNetworkStatus 5 }

   mGuardNetworkStatHTTPSRemAccess OBJECT-TYPE
     SYNTAX DisplayString
     ACCESS read-only
     STATUS mandatory
     DESCRIPTION
      "Status of HTTPS remote access (yes/no)."
    ::= { mGuardNetworkStatus 6 }

   mGuardNetworkStatSSHRemoteAccess OBJECT-TYPE
     SYNTAX DisplayString
     ACCESS read-only
     STATUS mandatory
     DESCRIPTION
      "Status of SSH remote access (yes/no)."
    ::= { mGuardNetworkStatus 7 }

   mGuardNetworkSoftwareVersion OBJECT-TYPE
     SYNTAX DisplayString
     ACCESS read-only
     STATUS mandatory
     DESCRIPTION
      "Current software version."
    ::= { mGuardNetworkStatus 8 }

   mGuardNetworkStatUptime OBJECT-TYPE
     SYNTAX DisplayString
     ACCESS read-only
     STATUS mandatory
     DESCRIPTION
      "Uptime."
    ::= { mGuardNetworkStatus 9 }

   mGuardNetworkStatLanguage OBJECT-TYPE
     SYNTAX DisplayString
     ACCESS read-only
     STATUS mandatory
     DESCRIPTION
      "GAI Language."
    ::= { mGuardNetworkStatus 10 }

    mGuardSysProduct OBJECT-TYPE
      SYNTAX INTEGER {
                        unknown(1),
                        eagle-tx-tx(500),
                        eagle-tx-mm-sc(501),
                        eagle-tx-sm-sc(502),
                        eagle-tx-lh-sc(503),
                        eagle-mm-sc-tx(504),
                        eagle-mm-sc-mm-sc(505),
                        eagle-mm-sc-sm-sc(506),
                        eagle-mm-sc-lh-sc(507),
                        eagle-fw-tx-tx(520),
                        eagle-fw-tx-mm-sc(521),
                        eagle-fw-tx-sm-sc(522),
                        eagle-fw-tx-lh-sc(523),
                        eagle-fw-mm-sc-tx(524),
                        eagle-fw-mm-sc-mm-sc(525),
                        eagle-fw-mm-sc-sm-sc(526),
                        eagle-fw-mm-sc-lh-sc(527),
                        eagle-mguard-tx-tx(530),
                        eagle-mguard-tx-mm-sc(531),
                        eagle-mguard-tx-sm-sc(532),
                        eagle-mguard-tx-lh-sc(533),
                        eagle-mguard-mm-sc-tx(534),
                        eagle-mguard-mm-sc-mm-sc(535),
                        eagle-mguard-mm-sc-sm-sc(536),
                        eagle-mguard-mm-sc-lh-sc(537),
                        rr-epl-tx-tx(550),
                        rr-epl-tx-mm-sc(551),
                        mGuard-smart-pr(51001),
                        mGuard-core-266(51002),
                        mGuard-smart-gw-266(51003),
                        mGuard-smart-enxl(51011),
                        mGuard-core-533(51012),
                        mGuard-smart-gw-533(51013),
                        mGuard-smart(51020),
                        mGuard-smart-en(51021),
                        mGuard-pci(51030),
                        mGuard-pci-pr(51031),
                        mGuard-pci-en(51032),
                        mGuard-pci-enxl(51033),
                        mGuard-industrial-enfw(51040),
                        mGuard-industrial-enxl(51044),
                        mGuard-blade-en(51052),
                        mGuard-blade-enxl(51053),
                        mGuard-delta(51060),
                        mGuard-delta-en(51062),
                        mGuard-delta-enxl(51063),
                        mGuard-smart-266(10101020),
                        mGuard-smart-533(10101050),
                        mGuard-PCI-266(10102020),
                        mGuard-PCI-533(10102050),
                        mGuard-delta-533(10103050),
                        mGuard-blade-266(10104020),
                        mGuard-blade-533(10104050),
                        mGuard-smart-266-Bundle-VPN(20101010),
                        mGuard-smart-533-Bundle-VPN(20101020),
                        mGuard-smart-533-Bundle-AV(20102000),
                        mGuard-delta-533-Bundle-VPN(20201000),
                        mGuard-delta-533-Bundle-AV(20202000)
                     }
      ACCESS read-only
      STATUS mandatory
      DESCRIPTION
       "Manufacturer-defined product identifier."
    ::= { mGuardSystem 9 }

    mGuardHardware OBJECT-TYPE
     SYNTAX DisplayString
     ACCESS read-only
     STATUS mandatory
     DESCRIPTION
       "The hardware of the mGuard."
    ::= { mGuardHardwareInformation 1 }

    mGuardCPU OBJECT-TYPE
     SYNTAX DisplayString
     ACCESS read-only
     STATUS mandatory
     DESCRIPTION
       "The CPU name."
    ::= { mGuardHardwareInformation 2 }

    mGuardCPUFamily OBJECT-TYPE
     SYNTAX DisplayString
     ACCESS read-only
     STATUS mandatory
     DESCRIPTION
       "The CPU family."
    ::= { mGuardHardwareInformation 3 }

    mGuardCPUStepping OBJECT-TYPE
     SYNTAX DisplayString
     ACCESS read-only
     STATUS mandatory
     DESCRIPTION
       "The CPU stepping."
    ::= { mGuardHardwareInformation 4 }

   mGuardCPUSpeed OBJECT-TYPE
     SYNTAX DisplayString
     ACCESS read-only
     STATUS mandatory
     DESCRIPTION
       "The CPU speed in MHz."
    ::= { mGuardHardwareInformation 5 }

   mGuardSystemTemperature OBJECT-TYPE
     SYNTAX DisplayString
     ACCESS read-only
     STATUS mandatory
     DESCRIPTION
       "The current system temperature (in degrees Celsius)."
    ::= { mGuardHardwareInformation 6 }

    mGuardUptime OBJECT-TYPE
     SYNTAX DisplayString
     ACCESS read-only
     STATUS mandatory
     DESCRIPTION
       "The system uptime."
    ::= { mGuardHardwareInformation 7 }

    mGuardUSMem OBJECT-TYPE
     SYNTAX DisplayString
     ACCESS read-only
     STATUS mandatory
     DESCRIPTION
       "The userspace memory."
    ::= { mGuardHardwareInformation 8 }

    mGuardMAC1 OBJECT-TYPE
     SYNTAX DisplayString
     ACCESS read-only
     STATUS mandatory
     DESCRIPTION
       "The MAC address of the first network interface."
    ::= { mGuardHardwareInformation 9 }

    mGuardMAC2 OBJECT-TYPE
     SYNTAX DisplayString
     ACCESS read-only
     STATUS mandatory
     DESCRIPTION
       "The MAC address of the second network interface."
    ::= { mGuardHardwareInformation 10 }

    mGuardMAC3 OBJECT-TYPE
     SYNTAX DisplayString
     ACCESS read-only
     STATUS mandatory
     DESCRIPTION
       "The MAC address of the third network interface."
    ::= { mGuardHardwareInformation 11 }

    mGuardSerialNumber OBJECT-TYPE
     SYNTAX DisplayString
     ACCESS read-only
     STATUS mandatory
     DESCRIPTION
       "The system's serial number ."
    ::= { mGuardHardwareInformation 12 }

   mGuardVerParSet OBJECT-TYPE
     SYNTAX DisplayString
     ACCESS read-only
     STATUS mandatory
     DESCRIPTION
       "The parameterset version."
    ::= { mGuardHardwareInformation 13 }

    mGuardProductName OBJECT-TYPE
     SYNTAX DisplayString
     ACCESS read-only
     STATUS mandatory
     DESCRIPTION
       "The product name."
    ::= { mGuardHardwareInformation 14 }

    mGuardOEMName OBJECT-TYPE
     SYNTAX DisplayString
     ACCESS read-only
     STATUS mandatory
     DESCRIPTION
       "The name of the OEM."
    ::= { mGuardHardwareInformation 15 }

    mGuardOEMSerial OBJECT-TYPE
     SYNTAX DisplayString
     ACCESS read-only
     STATUS mandatory
     DESCRIPTION
       "The OEM serial number ."
    ::= { mGuardHardwareInformation 16 }

    mGuardManufacturer OBJECT-TYPE
     SYNTAX DisplayString
     ACCESS read-only
     STATUS mandatory
     DESCRIPTION
       "The system manufacturer."
    ::= { mGuardHardwareInformation 17 }

    mGuardManuDate OBJECT-TYPE
     SYNTAX DisplayString
     ACCESS read-only
     STATUS mandatory
     DESCRIPTION
       "Date of manufacturing."
    ::= { mGuardHardwareInformation 18 }

    mGuardBootLoader OBJECT-TYPE
     SYNTAX DisplayString
     ACCESS read-only
     STATUS mandatory
     DESCRIPTION
       "The bootloader used at production ."
    ::= { mGuardHardwareInformation 19 }

    mGuardHardwareVersion OBJECT-TYPE
     SYNTAX DisplayString
     ACCESS read-only
     STATUS mandatory
     DESCRIPTION
       "The hardware version."
    ::= { mGuardHardwareInformation 20 }

   mGuardRescueSystem OBJECT-TYPE
     SYNTAX DisplayString
     ACCESS read-only
     STATUS mandatory
     DESCRIPTION
       "The rescue system used at production ."
    ::= { mGuardHardwareInformation 21 }

   mGuardProdSoft OBJECT-TYPE
     SYNTAX DisplayString
     ACCESS read-only
     STATUS mandatory
     DESCRIPTION
       "The software used at production ."
    ::= { mGuardHardwareInformation 22 }

   mGuardHacID OBJECT-TYPE
     SYNTAX DisplayString
     ACCESS read-only
     STATUS mandatory
     DESCRIPTION
       "The HAC ID."
    ::= { mGuardHardwareInformation 23 }

   mGuardRevisionLevel OBJECT-TYPE
     SYNTAX DisplayString
     ACCESS read-only
     STATUS mandatory
     DESCRIPTION
       "The revisionlevel (v/c) of the appliance."
    ::= { mGuardHardwareInformation 24 }

   mGuardImei OBJECT-TYPE
     SYNTAX DisplayString
     ACCESS read-only
     STATUS mandatory
     DESCRIPTION
       "The IMEI (International Mobile Equipment Identity) of the built-in 2G/3G modem"
    ::= { mGuardHardwareInformation 25 }

   mGuardMeid OBJECT-TYPE
     SYNTAX DisplayString
     ACCESS read-only
     STATUS mandatory
     DESCRIPTION
       "The MEID (mobile equipment identifier) of the built-in 2G/3G modem"
    ::= { mGuardHardwareInformation 26 }

   mGuardCpuTemperature OBJECT-TYPE
     SYNTAX DisplayString
     ACCESS read-only
     STATUS mandatory
     DESCRIPTION
       "The current CPU temperature (in degrees Celsius)."
    ::= { mGuardHardwareInformation 27 }

    mGuardVersion OBJECT-TYPE
     SYNTAX DisplayString
     ACCESS read-only
     STATUS mandatory
     DESCRIPTION
       "The current version."
    ::= { mGuardVersions 1 }

    mGuardBaseVersion OBJECT-TYPE
     SYNTAX DisplayString
     ACCESS read-only
     STATUS mandatory
     DESCRIPTION
       "The base version."
    ::=  { mGuardVersions 2 }

    mGuardUpdates OBJECT-TYPE
     SYNTAX DisplayString
     ACCESS read-only
     STATUS mandatory
     DESCRIPTION
       "Performed updates."
     ::= { mGuardVersions 3 }

    mGuardPackageVersionTable OBJECT-TYPE
      SYNTAX SEQUENCE OF MGuardPackageVersionEntry
      ACCESS not-accessible
      STATUS mandatory
      DESCRIPTION
       "Package descriptions."
    ::= { mGuardVersions 4 }

     mGuardPackageVersionEntry OBJECT-TYPE
      SYNTAX MGuardPackageVersionEntry
      ACCESS not-accessible
      STATUS mandatory
      DESCRIPTION
       "Description of a single package."
      INDEX { mGuardPkgIndex }
    ::= { mGuardPackageVersionTable 1 }

    MGuardPackageVersionEntry ::= SEQUENCE
    {
      mGuardPkgIndex  INTEGER,
      mGuardPkgName   DisplayString,
      mGuardPkgVerNum DisplayString,
      mGuardPkgVerVersion DisplayString,
      mGuardPkgVerFlavour DisplayString
    }

    mGuardPkgIndex OBJECT-TYPE
     SYNTAX INTEGER (1..2147483647)
     ACCESS not-accessible
     STATUS mandatory
     DESCRIPTION
       "Index to identify package."
    ::= {mGuardPackageVersionEntry 1 }

    mGuardPkgName OBJECT-TYPE
     SYNTAX DisplayString
     ACCESS read-only
     STATUS mandatory
     DESCRIPTION
       "Package name."
    ::= {mGuardPackageVersionEntry 2 }

    mGuardPkgVerNum OBJECT-TYPE
     SYNTAX DisplayString
     ACCESS read-only
     STATUS mandatory
     DESCRIPTION
       "Package version number."
    ::= {mGuardPackageVersionEntry 3 }

    mGuardPkgVerVersion OBJECT-TYPE
     SYNTAX DisplayString
     ACCESS read-only
     STATUS mandatory
     DESCRIPTION
       "Package version."
    ::= {mGuardPackageVersionEntry 4 }

    mGuardPkgVerFlavour OBJECT-TYPE
     SYNTAX DisplayString
     ACCESS read-only
     STATUS mandatory
     DESCRIPTION
       "Package flavour."
    ::= {mGuardPackageVersionEntry 5 }

   mGuardRouterRedundancyState OBJECT-TYPE
      SYNTAX INTEGER {
                        backup(1),
            master(2),
                        fault(3),
            disabled(4)
                     }
      ACCESS read-only
      STATUS obsolete
      DESCRIPTION
         "Current HA cluster state."
   ::= { mGuardRouterRedundancy 14 }

   mGuardRRedStateSSV OBJECT-TYPE
      SYNTAX INTEGER {
                        booting(1),
                        faultyWaiting(2),
                        faulty(3),
                        outdated(4),
                        outdatedWaiting(5),
                        standby(6),
                        standbyWaiting(7),
                        becomesActive(8),
                        active(9),
                        activeWaiting(10),
                        becomesStandby(11),
            unknown(9999)
                     }
      ACCESS read-only
      STATUS mandatory
      DESCRIPTION
         "General state of the router redundancy (state supervision).
          If the redundancy is disabled, the mGuard is forwarding
          traffic and thus active."
   ::= { mGuardRRedState 1 }

   mGuardRRedStateVIC OBJECT-TYPE
      SYNTAX INTEGER {
                        disabled(1),
                        justForwarding(2),
                        enabled(3),
            unknown(9999)
                     }
      ACCESS read-only
      STATUS mandatory
      DESCRIPTION
         "State of the Virtual Interfaces and traffic forwarding.
          disabled: no traffic is forwarded no ARP requests are responded.
          justForwarding: traffic is forwarded but no ARP response is sent.
          enabled: traffic is forwarded and ARP requests are responded.
          If the redundancy is disabled, traffic is forwarded and ARP requests
          are responded."
   ::= { mGuardRRedState 2 }

   mGuardRRedStateACSummary OBJECT-TYPE
      SYNTAX INTEGER {
                        success(1),
                        failure(2),
                        failureTotally(3),
            unknown(9999)
                     }
      ACCESS read-only
      STATUS mandatory
      DESCRIPTION
         "Summary state of the availability check.
          success: there is another mGuard that is and shall stay active.
          failure: there is another active mGuard that shall step back
                   to standby.
          failureTotally: there is no other mGuard."
   ::= { mGuardRRedStateAC 1 }

   mGuardRRedStateACInt OBJECT-TYPE
      SYNTAX INTEGER {
                        success(1),
                        failure(2),
                        failureTotally(3),
            unknown(9999)
                     }
      ACCESS read-only
      STATUS mandatory
      DESCRIPTION
         "State of the availability check on the internal interface.
          success: there is another mGuard that is and shall stay active.
          failure: there is another active mGuard that shall step back
                   to standby.
          failureTotally: there is no other mGuard."
   ::= { mGuardRRedStateAC 2 }

   mGuardRRedStateACExt OBJECT-TYPE
      SYNTAX INTEGER {
                        success(1),
                        failure(2),
                        failureTotally(3),
            unknown(9999)
                     }
      ACCESS read-only
      STATUS mandatory
      DESCRIPTION
         "State of the availability check on the external interface.
          success: there is another mGuard that is and shall stay active.
          failure: there is another active mGuard that shall step back
                   to standby.
          failureTotally: there is no other mGuard."
   ::= { mGuardRRedStateAC 3 }

   mGuardRRedStateACSync OBJECT-TYPE
      SYNTAX INTEGER {
                        success(1),
                        failure(2),
                        failureTotally(3),
            unknown(9999)
                     }
      ACCESS read-only
      STATUS mandatory
      DESCRIPTION
         "State of the availability check on the sync interface.
          If no separate sync interface is defined the sync state
          is unknown.
          success: there is another mGuard that is and shall stay active.
          failure: there is another active mGuard that shall step back
                   to standby.
          failureTotally: there is no other mGuard."
   ::= { mGuardRRedStateAC 4 }

   mGuardRRedStateACBridge OBJECT-TYPE
      SYNTAX INTEGER {
                        success(1),
                        failure(2),
                        failureTotally(3),
            unknown(9999)
                     }
      ACCESS read-only
      STATUS mandatory
      DESCRIPTION
         "State of the availability check on the bridge interface.
          If not applicable the state is unknown.
          success: there is another mGuard that is and shall stay active.
          failure: there is another active mGuard that shall step back
                   to standby.
          failureTotally: there is no other mGuard."
   ::= { mGuardRRedStateAC 5 }

   mGuardRRedStateCCSummary OBJECT-TYPE
      SYNTAX INTEGER {
                        success(1),
                        failure(2),
            unknown(9999)
                     }
      ACCESS read-only
      STATUS mandatory
      DESCRIPTION
         "Summary state of the connectivity check. If redundancy is
          disabled the status is always 'success'."
   ::= { mGuardRRedStateCC 1 }

   mGuardRRedStateCCInt OBJECT-TYPE
      SYNTAX INTEGER {
                        success(1),
                        failure(2),
            unknown(9999)
                     }
      ACCESS read-only
      STATUS mandatory
      DESCRIPTION
         "State of the connectivity check on the internal interface."
   ::= { mGuardRRedStateCC 2 }

   mGuardRRedStateCCExt OBJECT-TYPE
      SYNTAX INTEGER {
                        success(1),
                        failure(2),
            unknown(9999)
                     }
      ACCESS read-only
      STATUS mandatory
      DESCRIPTION
         "State of the connectivity check on the external interface."
   ::= { mGuardRRedStateCC 3 }

   mGuardRRedStateStateRepSummary OBJECT-TYPE
      SYNTAX INTEGER {
                        upToDate(1),
                        outdated(2),
                        sentFinal(3),
                        rcvdFinal(4),
            unknown(9999)
                     }
      ACCESS read-only
      STATUS mandatory
      DESCRIPTION
         "Summary of the Replication state.
          upToDate: the database(s) are up to date.
          outdated: the database(s) are not all up to date.
          sentFinal: transitional state.
          rcvdFinal: transitional state.
          An active mGuard is upToDate by definition."
   ::= { mGuardRRedStateStateRep 1 }

   mGuardRRedStateStateRepBridge OBJECT-TYPE
      SYNTAX INTEGER {
                        upToDate(1),
                        outdated(2),
                        sentFinal(3),
                        rcvdFinal(4),
            unknown(9999)
                     }
      ACCESS read-only
      STATUS mandatory
      DESCRIPTION
         "Replication state of the bridge forward database.
          upToDate: the database is up to date.
          outdated: the database is not up to date.
          sentFinal: transitional state.
          rcvdFinal: transitional state."
   ::= { mGuardRRedStateStateRep 2 }

   mGuardRRedStateStateRepFW OBJECT-TYPE
      SYNTAX INTEGER {
                        upToDate(1),
                        outdated(2),
                        sentFinal(3),
                        rcvdFinal(4),
            unknown(9999)
                     }
      ACCESS read-only
      STATUS mandatory
      DESCRIPTION
         "Replication state of the firewall connection tracking table.
          upToDate: the database is up to date.
          outdated: the database is not up to date.
          sentFinal: transitional state.
          rcvdFinal: transitional state."
   ::= { mGuardRRedStateStateRep 3 }

   mGuardRRedStateStateRepVPN OBJECT-TYPE
      SYNTAX INTEGER {
                        upToDate(1),
                        outdated(2),
                        sentFinal(3),
                        rcvdFinal(4),
            unknown(9999)
                     }
      ACCESS read-only
      STATUS mandatory
      DESCRIPTION
         "Replication state of the IPsec SA table.
          upToDate: the database is up to date.
          outdated: the database is not up to date.
          sentFinal: transitional state.
          rcvdFinal: transitional state."
   ::= { mGuardRRedStateStateRep 4 }

   mGuardRRedStatePhraseSwapAvail OBJECT-TYPE
      SYNTAX INTEGER {
                        none(1),
                        current(2),
                        phase0(3),
                        phase1(4),
                        phase2(5),
                        phase3(6),
                        phase4(7),
                        phase5(8),
            unknown(9999)
                     }
      ACCESS read-only
      STATUS mandatory
      DESCRIPTION
         "State of the process which maintains the swapping of an old
          phrase with the currently configured one for the availability check.
          none: The firmware or a component is (re)starting.
          current: The configured phrase is in use (and no other).
          phase0: The old phrase is in use for sending and receiving and the use of the configured phrase is being prepared.
          phase1: The old phrase is in use for sending and receiving and the configured phrase is installed for receiving messages.
          phase2: The configured phrase is in use for sending and receiving but the old phrase is still installed for receiving messages.
          phase3: This phase should not occur for the availability check.
          phase4: This phase should not occur for the availability check.
          phase5: This phase should not occur for the availability check.
          unknown: The component did not yet report a status."
   ::= { mGuardRRedStatePhraseSwap 2 }

   mGuardRRedStatePhraseSwapRepEncr OBJECT-TYPE
      SYNTAX INTEGER {
                        none(1),
                        current(2),
                        phase0(3),
                        phase1(4),
                        phase2(5),
                        phase3(6),
                        phase4(7),
                        phase5(8),
            unknown(9999)
                     }
      ACCESS read-only
      STATUS mandatory
      DESCRIPTION
         "State of the process which maintains the swapping of an old
          phrase with the currently configured one for the availability check.
          none: The firmware or a component is (re)starting.
          current: The configured phrase is in use (and no other).
          phase0: The old phrase is in use for sending and receiving and the use of the configured phrase is being prepared.
          phase1: The old phrase is in use for sending and receiving and the configured phrase is installed for receiving messages.
          phase2: The configured phrase is in use for sending and receiving but the old phrase is still installed for receiving messages.
          phase3: The configured phrase is in use (and no other) but the SPI is currently being reset (first step).
          phase4: The configured phrase is in use (and no other) but the SPI is currently being reset (second step).
          phase5: The configured phrase is in use (and no other) but the SPI is currently being reset (third step).
          unknown: The component did not yet report a status."
   ::= { mGuardRRedStatePhraseSwap 3 }

   mGuardHTTPSLastAccessIP OBJECT-TYPE
    SYNTAX IpAddress
    ACCESS read-only
    STATUS mandatory
    DESCRIPTION
       "Address of the last IP from which an authentication information
        was sent for HTTPS access."
   ::= { mGuardInfo 1 }

   mGuardShellLastAccessIP OBJECT-TYPE
    SYNTAX IpAddress
    ACCESS read-only
    STATUS mandatory
    DESCRIPTION
       "Address of the last IP from which a login event occurred."
   ::= { mGuardInfo 2 }

   mGuardDHCPLastAccessMAC OBJECT-TYPE
    SYNTAX MacAddress
    ACCESS read-only
    STATUS mandatory
    DESCRIPTION
       "MAC Address of the last unknown client trying to obtain a lease."
   ::= { mGuardInfo 3 }


  mGuardBladeRackID OBJECT-TYPE
    SYNTAX INTEGER
    ACCESS read-write
    STATUS mandatory
    DESCRIPTION
      "Blade rack ID, read-only on a blade, read-write on a controller"
  ::= { mGuardBlade 1 }

  mGuardBladeSlotID OBJECT-TYPE
    SYNTAX INTEGER
    ACCESS not-accessible
    STATUS mandatory
    DESCRIPTION
      "Blade slot ID, slot ID in a mGuard Rack"
  ::= { mGuardBlade 2 }


  mGuardBladeCtrlTable OBJECT-TYPE
    SYNTAX SEQUENCE OF  MGuardBladeCtrlEntry
    ACCESS not-accessible
    STATUS mandatory
    DESCRIPTION
      "Overview of controlled blades."
   ::= { mGuardBlade 3 }

  mGuardBladeCtrlEntry OBJECT-TYPE
      SYNTAX MGuardBladeCtrlEntry
      ACCESS not-accessible
      STATUS mandatory
      DESCRIPTION
       "A single update server repository. "
      INDEX { mGuardBladeCtrlIndex }
  ::= { mGuardBladeCtrlTable 1 }

  MGuardBladeCtrlEntry  ::= SEQUENCE {
     mGuardBladeCtrlIndex INTEGER,
     mGuardBladeCtrlDevice DisplayString,
     mGuardBladeCtrlStatus INTEGER,
     mGuardBladeCtrlAVRRevision DisplayString,
     mGuardBladeCtrlSlotID DisplayString,
     mGuardBladeCtrlProductID DisplayString,
     mGuardBladeCtrlAssemblyID DisplayString,
     mGuardBladeCtrlSerial DisplayString,
     mGuardBladeCtrlFlashID DisplayString,
     mGuardBladeCtrlVersion DisplayString,
     mGuardBladeCtrlBackup INTEGER,
     mGuardBladeCtrlRestore INTEGER
  }

  mGuardBladeCtrlIndex OBJECT-TYPE
    SYNTAX INTEGER (1..2147483647)
    ACCESS not-accessible
    STATUS mandatory
    DESCRIPTION
      "Table index."
   ::= { mGuardBladeCtrlEntry 1 }

   mGuardBladeCtrlDevice OBJECT-TYPE
    SYNTAX DisplayString
    ACCESS read-only
    STATUS mandatory
    DESCRIPTION
      "The name of the device inside the slot."
   ::= { mGuardBladeCtrlEntry 2 }

   mGuardBladeCtrlStatus OBJECT-TYPE
    SYNTAX INTEGER {
      absent(1),
      present(2),
      online(3)
    }
    ACCESS read-only
    STATUS mandatory
    DESCRIPTION
      "The status of the blade/slot."
   ::= { mGuardBladeCtrlEntry 3 }

   mGuardBladeCtrlAVRRevision OBJECT-TYPE
    SYNTAX DisplayString
    ACCESS read-only
    STATUS mandatory
    DESCRIPTION
      "The AVR revision of the blades bus controller."
   ::= { mGuardBladeCtrlEntry 4 }

   mGuardBladeCtrlSlotID OBJECT-TYPE
    SYNTAX DisplayString
    ACCESS read-only
    STATUS mandatory
    DESCRIPTION
      "The blades slot ID, as seen by the blade."
   ::= { mGuardBladeCtrlEntry 5 }

   mGuardBladeCtrlProductID OBJECT-TYPE
    SYNTAX DisplayString
    ACCESS read-only
    STATUS mandatory
    DESCRIPTION
      "The blades product ID."
   ::= { mGuardBladeCtrlEntry 6 }

   mGuardBladeCtrlAssemblyID OBJECT-TYPE
    SYNTAX DisplayString
    ACCESS read-only
    STATUS mandatory
    DESCRIPTION
      "The blades assembly ID."
   ::= { mGuardBladeCtrlEntry 7 }

   mGuardBladeCtrlSerial OBJECT-TYPE
    SYNTAX DisplayString
    ACCESS read-only
    STATUS mandatory
    DESCRIPTION
      "The blades serial number."
   ::= { mGuardBladeCtrlEntry 8 }

   mGuardBladeCtrlFlashID OBJECT-TYPE
    SYNTAX DisplayString
    ACCESS read-only
    STATUS mandatory
    DESCRIPTION
      "The blades Flash ID."
   ::= { mGuardBladeCtrlEntry 9 }

   mGuardBladeCtrlVersion OBJECT-TYPE
    SYNTAX DisplayString
    ACCESS read-only
    STATUS mandatory
    DESCRIPTION
      "The blades software version."
   ::= { mGuardBladeCtrlEntry 10 }

   mGuardBladeCtrlBackup OBJECT-TYPE
    SYNTAX INTEGER {
      yes(1),
      no(2)
    }
    ACCESS read-write
    STATUS mandatory
    DESCRIPTION
      "Whether to automatically pull the configuration off the blade/slot."
   ::= { mGuardBladeCtrlEntry 11 }

   mGuardBladeCtrlRestore OBJECT-TYPE
    SYNTAX INTEGER {
      yes(1),
      no(2)
    }
    ACCESS read-write
    STATUS mandatory
    DESCRIPTION
      "Whether to automatically push the configuration to the blade freshly inserted into the slot."
   ::= { mGuardBladeCtrlEntry 12 }


  mGuardBladePwrTable OBJECT-TYPE
    SYNTAX SEQUENCE OF  MGuardBladePwrEntry
    ACCESS not-accessible
    STATUS mandatory
    DESCRIPTION
      "Overview of controlled power supplies."
   ::= { mGuardBlade 4 }

  mGuardBladePwrEntry OBJECT-TYPE
      SYNTAX MGuardBladePwrEntry
      ACCESS not-accessible
      STATUS mandatory
      DESCRIPTION
       "Table entry."
      INDEX { mGuardBladePwrIndex }
  ::= { mGuardBladePwrTable 1 }

  MGuardBladePwrEntry  ::= SEQUENCE {
     mGuardBladePwrIndex INTEGER,
     mGuardBladePwrStatus INTEGER
  }

  mGuardBladePwrIndex OBJECT-TYPE
    SYNTAX INTEGER (1..2147483647)
    ACCESS not-accessible
    STATUS mandatory
    DESCRIPTION
      "Table index."
   ::= { mGuardBladePwrEntry 1 }

   mGuardBladePwrStatus OBJECT-TYPE
    SYNTAX INTEGER {
      absent(1),
      fatal(2),
      defect(3),
      ok(4)
    }
    ACCESS read-only
    STATUS mandatory
    DESCRIPTION
      "Status of the power supply."
   ::= { mGuardBladePwrEntry 2 }

  mGuardPSTable OBJECT-TYPE
     SYNTAX SEQUENCE OF MGuardPSEntry
     ACCESS not-accessible
     STATUS mandatory
     DESCRIPTION
    "This table contains all variables related to the power supply
         units of the chassis/switch. For each power supply slot exists
     one instance."
   ::= { mGuardTResIndustrialPower 2 }

  mGuardPSEntry OBJECT-TYPE
     SYNTAX MGuardPSEntry
     ACCESS not-accessible
     STATUS mandatory
     DESCRIPTION "Power supply entry"
     INDEX  { mGuardPSSysID, mGuardPSID }
   ::= { mGuardPSTable 1 }

  MGuardPSEntry ::= SEQUENCE {
     mGuardPSSysID INTEGER,
     mGuardPSID INTEGER,
     mGuardPSState INTEGER
  }

  mGuardPSSysID OBJECT-TYPE
     SYNTAX INTEGER (1..2147483647)
     ACCESS not-accessible
     STATUS mandatory
     DESCRIPTION
        "The value of SysID is assigned so as to uniquely identify a
         chassis/switch among the subordinate managed objects of the
         system."
   ::= { mGuardPSEntry 1 }

  mGuardPSID OBJECT-TYPE
     SYNTAX INTEGER(1..2147483647)
     ACCESS not-accessible
     STATUS mandatory
     DESCRIPTION
        "This Index is used to identify the associated power supply unit."
   ::= { mGuardPSEntry 2 }

  mGuardPSState OBJECT-TYPE
     SYNTAX INTEGER {
                 ok (1),
         failed (2),
         notInstalled (3),
         unknown (4)
     }
     ACCESS read-only
     STATUS mandatory
     DESCRIPTION
        "Indicates the operational state of the associated power supply. If
     the value of this variable changes, a mGuardPowerSupply trap is sent."
   ::= { mGuardPSEntry 3 }

  mGuardCMDStateTable OBJECT-TYPE
    SYNTAX SEQUENCE OF MGuardCMDStateEntry
    ACCESS not-accessible
    STATUS mandatory
    DESCRIPTION
      "Table of variables related to the state of service input/CMD
      switches or buttons."
    ::= { mGuardTResCMD 1 }

  mGuardCMDStateEntry OBJECT-TYPE
    SYNTAX MGuardCMDStateEntry
    ACCESS not-accessible
    STATUS mandatory
    DESCRIPTION
      "Service input/CMD state entry."
    INDEX { mGuardCMDStateSysId, mGuardCMDStateIndex }
    ::= { mGuardCMDStateTable 1 }

  MGuardCMDStateEntry ::= SEQUENCE {
    mGuardCMDStateSysId INTEGER,
    mGuardCMDStateIndex INTEGER,
    mGuardCMDState      INTEGER
  }

  mGuardCMDStateSysId OBJECT-TYPE
    SYNTAX INTEGER(1..2147483647)
    ACCESS not-accessible
    STATUS mandatory
    DESCRIPTION
      "System identifier containing the associated service input/CMD
      switch or button."
    ::= { mGuardCMDStateEntry 1 }

  mGuardCMDStateIndex OBJECT-TYPE
    SYNTAX INTEGER(1..2147483647)
    ACCESS not-accessible
    STATUS mandatory
    DESCRIPTION
      "Index of the associated service input/CMD switch or button."
    ::= { mGuardCMDStateEntry 2 }

  mGuardCMDState OBJECT-TYPE
    SYNTAX INTEGER {
      on(1),
      off(2)
    }
    ACCESS read-only
    STATUS mandatory
    DESCRIPTION
      "State of the associated service input/CMD switch or button. If
      the state changes, a mGuardTrapCMDStateChange trap is sent."
    ::= { mGuardCMDStateEntry 3 }

  mGuardTResAutoConfigAdapterState OBJECT-TYPE
    SYNTAX INTEGER {
        notPresent(1),
        removed(2),
        ok(3),
        notInSync(4),
        outOfMemory(5),
        wrongMachine(6),
        checksumErr(7),
        genericErr(8)
    }
    ACCESS read-only
    STATUS mandatory
    DESCRIPTION
       "Trap sent when external config storage was accessed."
   ::= { mGuardTResIndustrial 4 }

   mGuardTResSignalRelaisState OBJECT-TYPE
      SYNTAX INTEGER
      ACCESS read-only
      STATUS mandatory
      DESCRIPTION
         "Current state of the signal relay (1=on, 2=off)."
   ::= { mGuardTResSignalRelais 1 }

   mGuardTResSignalRelaisReason OBJECT-TYPE
      SYNTAX OBJECT IDENTIFIER
      ACCESS read-only
      STATUS mandatory
      DESCRIPTION
         "Reason why the signal relay was triggered."
   ::= { mGuardTResSignalRelais 2 }

   mGuardTResSignalRelaisReasonIdx OBJECT-TYPE
      SYNTAX INTEGER
      ACCESS read-only
      STATUS mandatory
      DESCRIPTION
         "Reason number (ue0=1, ue1=2, number of TX bytes for eth)."
   ::= { mGuardTResSignalRelais 3 }

  mGuardTResSigLinkID   OBJECT-TYPE
    SYNTAX    INTEGER  (1..7)
    ACCESS    read-only
    STATUS    mandatory
    DESCRIPTION
     "This index is used to identify the associated link and
     corresponds with ifMauIfIndex."
    ::= { mGuardTResSignalLinkTable 1 }

  mGuardTResSigLinkAlarm   OBJECT-TYPE
    SYNTAX    INTEGER {
        on (1),
        off (2)
        }
    ACCESS    read-write
    STATUS    mandatory
    DESCRIPTION
                 "DURABLE:  { off:all }
                 Indicates whether an alarm for the signaling relay of the
                 associated link will be produced or not, so you can mask the
                 value of ifMauMediaAvailable."
    ::= { mGuardTResSignalLinkTable 2 }

  mGuardTResBladeRackID OBJECT-TYPE
      SYNTAX INTEGER
      ACCESS read-only
      STATUS mandatory
      DESCRIPTION
         "Rack ID in question when sending a Blade-related SNMP trap."
   ::= { mGuardTResBladeInfo 1 }

  mGuardTResBladeSlotNr OBJECT-TYPE
      SYNTAX INTEGER
      ACCESS read-only
      STATUS mandatory
      DESCRIPTION
         "Slot ID in question when sending a Blade-related SNMP trap."
   ::= { mGuardTResBladeInfo 2 }

  mGuardTResBladeCtrlPowerStatus OBJECT-TYPE
    SYNTAX INTEGER
                 {
           absent(1),
                   present(2),
                   online(3)
         }
      ACCESS read-only
      STATUS mandatory
      DESCRIPTION
         "Status of the BladePack's power supplies when sending an SNMP trap."
   ::= { mGuardTResBladeCTRL 2 }

  mGuardTResBladeCtrlRunStatus OBJECT-TYPE
    SYNTAX INTEGER
                 {
           absent(1),
                   present(2),
                   online(3)
         }
      ACCESS read-only
      STATUS mandatory
      DESCRIPTION
         "Status of the Blade's run status when sending an SNMP trap."
   ::= { mGuardTResBladeCTRL 3 }


  mGuardTResBladeCtrlCfgBackup OBJECT-TYPE
      SYNTAX INTEGER {
            downloaded(3)
                     }
      ACCESS read-only
      STATUS mandatory
      DESCRIPTION
         "Reason/details for configuration backup to Blade CTRL when sending an SNMP trap."
   ::= { mGuardTResBladeCtrlCfg 1 }

  mGuardTResBladeCtrlCfgRestored OBJECT-TYPE
      SYNTAX INTEGER {
            automatic(1),
            manual(2)
                     }
      ACCESS read-only
      STATUS mandatory
      DESCRIPTION
         "Reason for configuration restore from Blade CTRL when sending an SNMP trap."
   ::= { mGuardTResBladeCtrlCfg 2 }

   mGuardTResRedundacyReason OBJECT-TYPE
    SYNTAX DisplayString
    ACCESS read-only
    STATUS mandatory
    DESCRIPTION
       "Reason for redundancy status change."
   ::= { mGuardTResRedundancy 1 }

   mGuardTResRedundacyBackupDown OBJECT-TYPE
    SYNTAX DisplayString
    ACCESS read-only
    STATUS mandatory
    DESCRIPTION
       "Information sent by Master device when Backup device is not reachable."
   ::= { mGuardTResRedundancy 2 }

   mGuardTResUserFirewallUsername OBJECT-TYPE
    SYNTAX DisplayString
    ACCESS read-only
    STATUS mandatory
    DESCRIPTION
       "Name of the remote user."
   ::= { mGuardTResUserFirewall 1 }

   mGuardTResUserFirewallSrcIP OBJECT-TYPE
    SYNTAX IpAddress
    ACCESS read-only
    STATUS mandatory
    DESCRIPTION
       "Source IP the remote user is acting from."
   ::= { mGuardTResUserFirewall 2 }

   mGuardTResUserFirewallAuthMethod OBJECT-TYPE
    SYNTAX INTEGER
                 {
                   radius(1),
                   local(2)
                 }
    ACCESS  read-only
    STATUS mandatory
    DESCRIPTION
       "Authentication method: radius / local."
   ::= { mGuardTResUserFirewall 3 }

   mGuardTResUserFWLogoutReason OBJECT-TYPE
    SYNTAX INTEGER
                 {
                   manually(1),
                   timeout(2)
                 }
    ACCESS read-only
    STATUS mandatory
    DESCRIPTION
       "Reason of user logout: manually / timeout."
   ::= { mGuardTResUserFirewall 4 }

  mGuardTResVPNName OBJECT-TYPE
    SYNTAX DisplayString
    ACCESS read-only
    STATUS mandatory
    DESCRIPTION
      "The name of the VPN connection."
    ::= { mGuardTResVPN 1 }

  mGuardTResVPNIndex OBJECT-TYPE
    SYNTAX INTEGER
    ACCESS read-only
    STATUS mandatory
    DESCRIPTION
      "Row index in the connections tunnel/transport table. The first
      row has the number 1 (one)."
    ::= { mGuardTResVPN 2 }

  mGuardTResVPNPeer OBJECT-TYPE
    SYNTAX IpAddress
    ACCESS read-only
    STATUS mandatory
    DESCRIPTION
      "The IP address of the remote VPN gateway."
    ::= { mGuardTResVPN 3 }

  mGuardTResVPNStatus OBJECT-TYPE
    SYNTAX INTEGER  {
      waiting(1),
      inactive(2),
      up(3),
      down(4)
    }
    ACCESS read-only
    STATUS mandatory
    DESCRIPTION
       "The new status of the VPN connection."
    ::= { mGuardTResVPN 4 }

  mGuardTResVPNType OBJECT-TYPE
    SYNTAX INTEGER  {
      transport(1),
      tunnel(2)
    }
    ACCESS read-only
    STATUS mandatory
    DESCRIPTION
      "The type of the VPN connection."
    ::= { mGuardTResVPN 5 }

  mGuardTResVPNLocal OBJECT-TYPE
    SYNTAX DisplayString
    ACCESS read-only
    STATUS mandatory
    DESCRIPTION
      "The local network of the VPN connection in CIDR notation."
    ::= { mGuardTResVPN 6 }

  mGuardTResVPNRemote OBJECT-TYPE
    SYNTAX DisplayString
    ACCESS read-only
    STATUS mandatory
    DESCRIPTION
      "The remote network of the VPN connection in CIDR notation."
    ::= { mGuardTResVPN 7 }

  mGuardTResSSHRemoteIP OBJECT-TYPE
    SYNTAX IpAddress
    ACCESS read-only
    STATUS mandatory
    DESCRIPTION
      "The IP address the session has been established from."
    ::= { mGuardTResSSH 1 }

  mGuardTResSSHUsername OBJECT-TYPE
    SYNTAX DisplayString
    ACCESS read-only
    STATUS mandatory
    DESCRIPTION
      "The username identifying this session."
    ::= { mGuardTResSSH 2 }

  mGuardTResSECStickRemoteIP OBJECT-TYPE
    SYNTAX IpAddress
    ACCESS read-only
    STATUS mandatory
    DESCRIPTION
      "The IP address the session has been established from."
    ::= { mGuardTResSECStick 1 }

  mGuardTResSECStickUsername OBJECT-TYPE
    SYNTAX DisplayString
    ACCESS read-only
    STATUS mandatory
    DESCRIPTION
      "The username identifying this session."
    ::= { mGuardTResSECStick 2 }

  mGuardTResCIFSShare OBJECT-TYPE
    SYNTAX DisplayString
    ACCESS read-only
    STATUS mandatory
    DESCRIPTION
      "The name of the CIFS share that has been scanned."
    ::= { mGuardTResCIFSScan 1 }

  mGuardTResCIFSScanError OBJECT-TYPE
    SYNTAX INTEGER {
        internal(1),
        timeout(2),
        no-idb(3),
        inval-idb-inval-sig(4),
        inval-idb-algo-mismatch(5),
        inval-idb-uuid-mismatch(6),
        cshare-not-mounted(7),
        mshare-not-mounted(8),
        file-access(11),
        dir-traversal(12),
        access-check-ok(13),
        none(1000)
    }
    ACCESS read-only
    STATUS mandatory
    DESCRIPTION
      "The error that has occurred during the scan of the CIFS share, or
       'none' if the share has been scanned successfully."
    ::= { mGuardTResCIFSScan 2 }

  mGuardTResCIFSNumDiffs OBJECT-TYPE
    SYNTAX INTEGER(0..2147483647)
    ACCESS read-only
    STATUS mandatory
    DESCRIPTION
      "The number of discrepancies with respect to the previous scan of
       the CIFS share."
    ::= { mGuardTResCIFSScan 3 }


--
-- Traps with enterprise = mGuardb
--
mGuardHTTPSLoginTrap TRAP-TYPE
    ENTERPRISE	mGuardb
    VARIABLES	{ mGuardHTTPSLastAccessIP }
    DESCRIPTION
      "This trap is sent when someone is trying to open a HTTPS session.
          mGuardHTTPSLastAccessIP contains the IP address of the last
          login request."
    ::= 1

mGuardShellLoginTrap TRAP-TYPE
    ENTERPRISE	mGuardb
    VARIABLES	{ mGuardShellLastAccessIP }
    DESCRIPTION
        "This trap is sent when someone opens the shell through SSH or
         serial console. mGuardShellAccessLastIP contains the IP address of
         the login request. The value of mGuardShellAccessLastIP is 0.0.0.0,
         if the request was sent via serial console. "
    ::= 2

mGuardDHCPNewClientTrap TRAP-TYPE
    ENTERPRISE	mGuardb
    VARIABLES	{ mGuardDHCPLastAccessMAC }
    DESCRIPTION
        "This trap is sent when a DHCP request was received from an unknown
         client"
    ::= 3

mGuardSECStickConnectTrap TRAP-TYPE
    ENTERPRISE	mGuardb
    VARIABLES	{ mGuardSECStickLastAccessIP }
    DESCRIPTION
        "This trap is sent when a connection to a SEC-Stick server is
         opened. mGuardSECStickLastAccessIP contains the IP address of
             the connection peer."
    ::= 4

  mGuardTrapIndustrialPowerStatus TRAP-TYPE
   ENTERPRISE  mGuardTrapIndustrial
   VARIABLES  { mGuardPSState }
   DESCRIPTION
       "Trap sent when power supply failure was detected."
   ::= 2

  mGuardTrapIndustrialTemperature  TRAP-TYPE
   ENTERPRISE  mGuardTrapIndustrial
   VARIABLES  { mGuardSystemTemperature, mGuardTResIndustrialTempHiLimit, mGuardTResIndustrialTempLowLimit }
   DESCRIPTION
       "Trap reporting system temperature exceeding the given limits."
   ::= 1

  mGuardTrapIndustrialCpuTemperature  TRAP-TYPE
   ENTERPRISE  mGuardTrapIndustrial
   VARIABLES  { mGuardCpuTemperature, mGuardTResIndustrialCpuTempHiLimit, mGuardTResIndustrialCpuTempLowLimit }
   DESCRIPTION
       "Trap reporting CPU temperature exceeding the given limits."
   ::= 5

  mGuardTrapSignalRelais TRAP-TYPE
    ENTERPRISE  mGuardTrapIndustrial
    VARIABLES  { mGuardTResSignalRelaisState, mGuardTResSignalRelaisReason, mGuardTResSignalRelaisReasonIdx }
    DESCRIPTION
         "Current state of the signal relay changed (0=off, 1=on)."
   ::= 3

  mGuardTrapAutoConfigAdapterState TRAP-TYPE
   ENTERPRISE  mGuardTrapIndustrial
   VARIABLES  { mGuardTResAutoConfigAdapterState }
   DESCRIPTION
       "Trap sent when external config storage was accessed."
   ::= 4

  mGuardTrapBladeCtrlPowerStatus TRAP-TYPE
   ENTERPRISE  mGuardTrapBladeCTRL
   VARIABLES  { mGuardTResBladeRackID, mGuardTResBladeSlotNr, mGuardTResBladeCtrlPowerStatus }
   DESCRIPTION
         "BladePack's power supplies status changed."
   ::= 2

  mGuardTrapBladeCtrlRunStatus TRAP-TYPE
   ENTERPRISE  mGuardTrapBladeCTRL
   VARIABLES  { mGuardTResBladeRackID, mGuardTResBladeSlotNr, mGuardTResBladeCtrlRunStatus }
   DESCRIPTION
         "Blade's run status changed."
   ::= 3

  mGuardTrapBladeCtrlCfgBackup TRAP-TYPE
   ENTERPRISE  mGuardTrapBladeCtrlCfg
   VARIABLES  { mGuardTResBladeRackID, mGuardTResBladeSlotNr, mGuardTResBladeCtrlCfgBackup }
   DESCRIPTION
         "Configuration backup to Blade CTRL is triggered."
   ::= 1

  mGuardTrapBladeCtrlCfgRestored TRAP-TYPE
   ENTERPRISE  mGuardTrapBladeCtrlCfg
   VARIABLES  { mGuardTResBladeRackID, mGuardTResBladeSlotNr, mGuardTResBladeCtrlCfgRestored }
   DESCRIPTION
         "Configuration restore from Blade CTRL is triggered."
   ::= 2

   mGuardTrapRouterRedBackupDown TRAP-TYPE
    ENTERPRISE mGuardTrapRouterRedundancy
    VARIABLES  { mGuardTResRedundacyBackupDown }
    DESCRIPTION
       "Backup device  is not reachable by Master device (This trap is only sent, when ICMP checks are activated)."
   ::= 2

   mGuardTrapRRedundancyStatusChange TRAP-TYPE
    ENTERPRISE mGuardTrapRouterRedundancy
    VARIABLES  { mGuardRRedStateSSV, mGuardRRedStateACSummary, mGuardRRedStateCCSummary, mGuardRRedStateStateRepSummary }
    DESCRIPTION
       "Current HA cluster state changed."
   ::= 3

   mGuardTrapUserFirewallLogin TRAP-TYPE
    ENTERPRISE mGuardTrapUserFirewall
    VARIABLES  { mGuardTResUserFirewallUsername, mGuardTResUserFirewallSrcIP, mGuardTResUserFirewallAuthMethod  }
    DESCRIPTION
       "Remote User logged in."
   ::= 1

   mGuardTrapUserFirewallLogout TRAP-TYPE
    ENTERPRISE mGuardTrapUserFirewall
    VARIABLES  { mGuardTResUserFirewallUsername, mGuardTResUserFirewallSrcIP, mGuardTResUserFWLogoutReason }
    DESCRIPTION
       "Remote User logged out."
   ::= 2

   mGuardTrapUserFirewallAuthError TRAP-TYPE
    ENTERPRISE mGuardTrapUserFirewall
    VARIABLES  { mGuardTResUserFirewallUsername, mGuardTResUserFirewallSrcIP, mGuardTResUserFirewallAuthMethod  }
    DESCRIPTION
       "Authentication error occurred."
   ::= 3

mGuardTrapVPNIKEServerStatus TRAP-TYPE
        ENTERPRISE mGuardTrapVPN
        VARIABLES { mGuardTResVPNStatus }
        DESCRIPTION
          "This trap is send when the VPN IPsec IKE server going up or
           down."
        ::= 1

mGuardTrapVPNIPsecConnStatus TRAP-TYPE
        ENTERPRISE mGuardTrapVPN
        VARIABLES {
          mGuardTResVPNName, mGuardTResVPNIndex, mGuardTResVPNPeer,
          mGuardTResVPNStatus, mGuardTResVPNType, mGuardTResVPNLocal,
          mGuardTResVPNRemote
        }
        DESCRIPTION
          "This trap is send when the state of a VPN IPsec connection
          has changed. mGuardTResVPNStatus indicates the following state
          transitions:

                    --- waiting -->          -- up -->
           Inactive                 Waiting            Established
                    <-- inactive --         <-- down --
          "
        ::= 2

mGuardTrapVPNL2TPConnStatus TRAP-TYPE
        ENTERPRISE mGuardTrapVPN
        VARIABLES {
          mGuardTResVPNName, mGuardTResVPNIndex, mGuardTResVPNPeer,
          mGuardTResVPNStatus, mGuardTResVPNLocal, mGuardTResVPNRemote
        }
        DESCRIPTION
          "This trap is send when the state of a VPN L2TP connection
          changed."
        ::= 3

mGuardTrapSSHLogin TRAP-TYPE
        ENTERPRISE mGuardTrapSSH
        VARIABLES { mGuardTResSSHUsername, mGuardTResSSHRemoteIP }
        DESCRIPTION
          "This trap is send when a SSH session is established after
           sucessfull login."
        ::= 1

mGuardTrapSSHLogout TRAP-TYPE
        ENTERPRISE mGuardTrapSSH
        VARIABLES { mGuardTResSSHUsername, mGuardTResSSHRemoteIP }
        DESCRIPTION
          "This trap is send when a SSH session is closed."
        ::= 2

mGuardTrapSECStickLogin TRAP-TYPE
        ENTERPRISE mGuardTrapSECStick
        VARIABLES { mGuardTResSECStickUsername, mGuardTResSECStickRemoteIP }
        DESCRIPTION
          "This trap is send when a SEC-Stick session is established after
           sucessfull login."
        ::= 1

mGuardTrapSECStickLogout TRAP-TYPE
        ENTERPRISE mGuardTrapSECStick
        VARIABLES { mGuardTResSECStickUsername, mGuardTResSECStickRemoteIP }
        DESCRIPTION
          "This trap is send when a SEC-Stick session is closed."
        ::= 2

mGuardSECStickLastAccessIP OBJECT-TYPE
    SYNTAX IpAddress
    ACCESS read-only
    STATUS mandatory
    DESCRIPTION
       "Address of the last IP from which a login event occurred."
   ::= { mGuardInfo 14 }


mGuardTrapCIFSScanInfo TRAP-TYPE
  ENTERPRISE mGuardTrapCIFSScan
  VARIABLES { mGuardTResCIFSShare, mGuardTResCIFSScanError, mGuardTResCIFSNumDiffs }
  DESCRIPTION
    "A CIFS share has been scanned successfully. No discrepancies with
     respect to the previous scan (if any) have been detected."
  ::= 1

mGuardTrapCIFSScanFailure TRAP-TYPE
  ENTERPRISE mGuardTrapCIFSScan
  VARIABLES { mGuardTResCIFSShare, mGuardTResCIFSScanError, mGuardTResCIFSNumDiffs }
  DESCRIPTION
    "Scanning of a CIFS share could not be completed due to a failure."
  ::= 2

mGuardTrapCIFSScanDetection TRAP-TYPE
  ENTERPRISE mGuardTrapCIFSScan
  VARIABLES { mGuardTResCIFSShare, mGuardTResCIFSScanError, mGuardTResCIFSNumDiffs }
  DESCRIPTION
    "A CIFS share has been scanned and discrepancies with respect to the
     previous scan have been detected."
  ::= 3

mGuardTrapGSMIncomingSMS TRAP-TYPE
  ENTERPRISE mGuardTrapGSM
  VARIABLES { mGuardEDSGsmIncomingSMS }
  DESCRIPTION
    "An SMS is received"
  ::= 2

mGuardTrapGSMNetworkProbe TRAP-TYPE
  ENTERPRISE mGuardTrapGSM
  VARIABLES { mGuardEDSGsmNetworkProbe }
  DESCRIPTION
    "The status of the network probe changed"
  ::= 3

mGuardTrapCMDStateChange TRAP-TYPE
  ENTERPRISE mGuardTrapCMD
  VARIABLES { mGuardCMDState }
  DESCRIPTION
    "The state of a service input/CMD changed."
  ::= 1

END
